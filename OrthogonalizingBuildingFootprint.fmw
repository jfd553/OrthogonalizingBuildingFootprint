FME workspace OrthogonalizingBuildingFootprint.fmw

Parameters:
- MaxOrthogonalAngleError = 5   # Maximum error on orthogonal angles (deg)
- MaxCollinearAngleError = 1   # Maximum error on collinear angles (deg)
- MinOrthogonalSegmentLength = 0.25   # Minimum orthogonal segments length (m)
- SourceDataset_OSM = $(FME_MF_DIR)OrthogonalizingBuildingFootprint.osm   # Source OpenStreetMap File(s)
- SourceDataset_ESRISHAPE = E:\Geomatique\OpenStreetMap\OpenDataBuildings\20191205.Quebec\odb_quebec.shp   # Source Esri Shapefile(s)
- DestDataset_OSM = E:\Geomatique\OpenStreetMap\OpenDataBuildings\20191205.Quebec   # Destination OpenStreetMap (OSM) File

Readers:
- OSM_1: OSM from $(SourceDataset_OSM) in LL-WGS84
- ESRISHAPE_1: ESRISHAPE from $(SourceDataset_ESRISHAPE)

Writers:
- OSM_2: OSM to $(DestDataset_OSM)

odb_quebec (reader ESRISHAPE_1)
    attributes: OBJECTID long, Longitude double, Latitude double, CSDUID char(7), CSDNAME char(100), Data_prov char(254), Build_ID char(254), Shape_Leng double, Shape_Area double
    -> Deaggregator_2
Note: Outremont / 7.5,2.5,0.15 / 29 / 540 / 579 / 994 / 1546 / Toronto / (1) 5.0,2.5,0.75 / (2) 7.5,2.5,0.50 / 65,218,224,242,309,310 / 159-163 / 135 / 152 / 181 / 68 / 42 / 169,170 / 221,222 / 399,400 / 325-328 / Benchmark / 10.0,2.5,0.1 / 1-6
building (reader OSM_1)
    attributes: attribution xml_char(25), building xml_char(13), building:colour xml_char(10), building:material xml_char(9), canvec:CODE xml_decimal(8,0), canvec:UUID xml_char(33), cuisine xml_char(9), internet_access xml_char(5), opendata:type xml_decimal(7,0), operator xml_char(43), osm_area xml_char(4), phone xml_char(16), shop xml_char(15), website xml_char(40), wikipedia xml_char(29), source xml_buffer, addr:postcode xml_buffer, addr:city xml_buffer, amenity xml_buffer, name xml_buffer, tag{}.v xml_buffer, building:levels xml_buffer, tag{}.k xml_buffer, addr:housenumber xml_buffer, nd{}.ref xml_buffer, addr:street xml_buffer, addr:district xml_char(16), addr:housename xml_char(19), building:colour:note xml_char(16), building:flats xml_decimal(3,0),
      building:levels:source xml_char(37), building:min_level xml_decimal(2,0), built_date xml_decimal(5,0), description xml_char(37), disused:amenity xml_char(5), inscription xml_char(34), leisure xml_char(8), man_made xml_char(16), name:en xml_char(19), name:fr xml_char(27), note xml_char(173), old_name xml_char(43), opening_hours xml_char(12), outdoor_seating xml_char(6), roof:colour xml_char(6), shelter xml_boolean, smoking xml_char(8), source:addr:housenumber xml_char(7), source:addr:postcode xml_char(44), sport xml_char(11), stars xml_decimal(2,0), tag.layer xml_decimal(2,0), takeaway xml_boolean, wheelchair xml_char(4), wheelchair:description xml_char(13), wikidata xml_char(9), construction xml_buffer, fixme xml_buffer, military xml_buffer, tourism xml_buffer,
      height xml_buffer
    -> Deaggregator_2
Note: Result: Polygons have adequate geometry and attributes for processing
Cloner_2
    COPIES = 1
    COPY -> building
    COPY -> AttributeKeeper_7
building: Inspector [off]
Note: Result: Polygon’s origin (first/last vertex) is set on the polygon’s most right angle corner. Although not mandatory, it simplifies later computations for complex cases.
Note: Result: New coordinates values are known for every vertex. New coordinates insure a) orthogonal angles between segments for orthogonal sections, b) collinear segments when standard topology requires it, and c) unchanged angles between segments for non-orthogonal sections.
MeasureRemover
    REMOVE_ALL = Yes
    -> Chopper_4
odb_quebec (writer OSM_2)
    attributes: building xml_char(254), building:part xml_char(254), addr:city xml_char(254), building:rightangles xml_char(254), building:altered xml_char(254)
Note: Result: All polygons are rebuilt using new coordinates. All corners that were originally within λo from a right angle now show 90o corners. All nodes that were near collinear (within Ѳo or λo) are either removed or, when they were required to keep initial polygons’ topology, are exactly collinear. All polygons’ segments that were near collinear (within ɛ m) are now exactly collinear.
Note: Result: All orthogonalized polygons are back to their original projection and attributes. Four attributes are added to the polygons:
Result: Inspector

Bookmark: 0.0 Features validation
Deaggregator_2
    EXPLODE_INSTANCES = No
    GEOM_NAME_FIELD = _geometry_name
    LIST_ATTR_MODE_LOOKUP = LEAN
    MODE = Flatten All Levels
    SPLIT_COMPOSITES = No
    DEAGGREGATED -> GeometryValidator
GeometryValidator
    ISSUE_ATTR_NAME = _issues
    PRESETS = Custom
    REPAIR = Yes
    RULES = OGC_SIMPLE_CHECK  CONSECUTIVE_IDENTICAL_VERTICES_2D CHECK_Z]YES]TOLERANCE]0.00000001]FME_CONTROLLER_QUERY_FILE]transformers\dependencies\geometryvalidator\CONSECUTIVE_IDENTICAL_VERTICES_2D.fme
    SUMMARY = Detailed
    PASSED -> Counter_1
    REPAIRED -> Counter_1

Bookmark: 1.1.Object identifier (_id.object)
Counter_1
    CNT_ATTR = _id.object
    DOMAIN = buildings
    SCOPE = Global
    START = 1
    -> FeatureSelection
FeatureSelection: Tester
    BOOL_OP = OR
    TEST_CLAUSE:
      NUM_TEST @Value(_id.object) IN 1-6
      TEST _id.object ATTRIBUTE_HAS_A_VALUE ""
    TEST_MODE = TEST
    PASSED -> CommonLocalReprojector
CommonLocalReprojector
    PROJECTION_TYPE = Equidistant (AZMED)
    VERTICAL_HANDLING = Ignore heights and leave them unchanged
    -> AttributeKeeper_10
    -> Cloner_2
AttributeKeeper_10
    KEEP_ATTRS = _id.object
    -> 1.1.ObjectIdentifier
    -> DonutHoleExtractor_4
1.1.ObjectIdentifier: Inspector [off]

Bookmark: 5.5.AttributesRetriver&Reprojection
AttributeKeeper_7
    KEEP_ATTRS = CSDNAME,building,addr:city,addr:housenumber,_id.object,addr:street
    -> ChangeDetector [ORIGINAL]
    -> FeatureMerger_3 [SUPPLIER]
MeasureRemover_3
    REMOVE_ALL = Yes
    -> AttributeCreator_OSM_2
Note: building:rightangles
AttributeCreator_OSM_2
    ATTR_TABLE = SET_TO building:rightangles = @Value(orthogonalbuilding)
    -> CenterPointReplacer
    -> PointOnAreaOverlayer [AREA]
CenterPointReplacer
    POINTTYPE = INSIDE
    POINT -> PointOnAreaOverlayer [POINT]
PointOnAreaOverlayer
    DEAGGREGATE_INPUT = Yes
    GROUP_BY = _id.aggregate
    OV_ATTR = _overlaps
    POLYS_FIRST = NO
    POINT -> Tester_building:part
    AREA -> FeatureMerger_2 [REQUESTOR]
Note: building:part
Tester_building:part
    BOOL_OP = OR
    COMPOSITE_TEST = 1
    TEST_CLAUSE = TEST @Value(_overlaps) >= 2
    TEST_MODE = TEST
    PASSED -> FeatureMerger_2 [SUPPLIER]
    FAILED -> FeatureMerger_2 [SUPPLIER]
FeatureMerger_2
    ATTR_ACCUM_MODE = Merge Supplier
    ATTR_CONFLICT_RES = Use Requestor
    IGNORE_NULLS = No
    JOIN_KEYS = @Value(_id.object) @Value(_id.object) AUTO
    MERGE_TYPE = Attributes Only
    PROCESS_DUPS = NO
    REJECT_NULL_MISSING_KEYS = No
    SUPPLIERS_FIRST = No
    MERGED -> AttributeKeeper_16
AttributeKeeper_16
    KEEP_ATTRS = building:part,_id.object,building:rightangles
    -> FeatureMerger_3 [REQUESTOR]
FeatureMerger_3
    ATTR_ACCUM_MODE = Merge Supplier
    ATTR_CONFLICT_RES = Use Requestor
    IGNORE_NULLS = No
    JOIN_KEYS = @Value(_id.object) @Value(_id.object) AUTO
    MERGE_TYPE = Attributes Only
    PROCESS_DUPS = NO
    REJECT_NULL_MISSING_KEYS = No
    SUPPLIERS_FIRST = No
    MERGED -> ChangeDetector [REVISED]
    UNUSED_SUPPLIER -> ChangeDetector [REVISED]
ChangeDetector
    CHECK_COORDINATE_SYSTEMS = No
    LENIENT_MATCH = Yes
    MATCH = 2D
    PREEMPTIVE_ATTRS = _id.object
    UNCHANGED_OUTPUT = Output Revised
    UPDATED -> AttributeCreator_3
    DELETED -> AttributeCreator_5
    UNCHANGED -> AttributeCreator_5
Note: building:altered=yes
AttributeCreator_3
    ATTR_TABLE = SET_TO building:altered = yes
    -> TestFilter
Note: building:altered=no
AttributeCreator_5
    ATTR_TABLE = SET_TO building:altered = no
    -> TestFilter
TestFilter
    DEFAULT_VALUE = <UNFILTERED>
    TEST_LIST = "BOOL_OP,OR,COMPOSITE_TEST,""""""1"""""",TEST_CLAUSE,TEST building:part ATTRIBUTE_HAS_A_VALUE """,building:part,"BOOL_OP,OR,COMPOSITE_TEST,""""""1"""""",TEST_CLAUSE,TEST building ATTRIBUTE_HAS_A_VALUE """,building=*
    <UNFILTERED> -> AttributeCreator_7
    building:part -> AttributeRemover
    building=* -> AttributeCreator_OSM
AttributeRemover
    REMOVE_ATTRS = building
    -> AttributeRemover_3
AttributeCreator_7
    ATTR_TABLE = SET_TO building = yes
    -> AttributeCreator_OSM
Note: addr:city
AttributeCreator_OSM
    ATTR_TABLE = SET_TO addr:city = @Value(CSDNAME)
    -> AttributeRemover_3
AttributeRemover_3
    REMOVE_ATTRS = fme_db_operation,CSDNAME,_id.object
    -> Reprojector
    -> Result
Reprojector [off]
    DEST = LL-WGS84
    INTERPOLATION_TYPE_NAME = Nearest Neighbor
    RASTER_CELL_SIZE = Preserve Cells
    RASTER_TOLERANCE = 0.0
    SOURCE = Read from feature
    REPROJECTED -> odb_quebec (writer OSM_2)

Bookmark: 1.2.HolesExtraction
DonutHoleExtractor_4
    DEAGGREGATE_INPUT = Yes
    OUTERSHELL -> SpatialFilter [Candidate]
    OUTERSHELL -> 1.2.HolesExtraction-OuterShells
    OUTERSHELL -> Dissolver
    HOLE -> AttributeCreator_10
1.2.HolesExtraction-OuterShells: Inspector [off]
AttributeCreator_10
    ATTR_TABLE = SET_TO _id.partOf = @Value(_id.object)
    -> Counter_2
Counter_2
    CNT_ATTR = _id.object
    DOMAIN = buildings
    SCOPE = Global
    START = 1
    -> SpatialFilter [Candidate]
    -> 1.2.HolesExtraction-InnerShells
1.2.HolesExtraction-InnerShells: Inspector [off]

Bookmark: 1.3.AggregateIdentification
Dissolver
    ACCUM_INPUT_ATTRS = Drop Incoming Attributes
    CLEANING_TOLERANCE = None
    CONNECT_Z_MODE = First Wins
    DEAGGREGATE_INPUT = Yes
    NO_OVRLP = No
    AREA -> Counter_5
Counter_5
    CNT_ATTR = _id.aggregate
    DOMAIN = counter
    SCOPE = Global
    START = 0
    -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDICATES = CONTAINS
    USE_BOUNDING_BOX = No
    PASSED -> AttributeRemover_7
AttributeRemover_7
    -> linearizeCollinearSegments
    -> 1.3.AggregateIdentification
1.3.AggregateIdentification: Inspector [off]
    TACKATTRS = _id.aggregate

Bookmark: 1.4.LinearizeNear-CollinearVertices
linearizeCollinearSegments: LinearizeSegments
    MaxCollinearAngleError = $(MaxCollinearAngleError)
    MinOrthogonalSegmentLength = $(MinOrthogonalSegmentLength)
    _ID.OBJECT = @Value(_id.object)
    -> 1.4.LinearizeNear-CollinearVertices_-_polygons
    -> PolygonOriginIdentifier
    Changes -> 1.4.LinearizeNear-CollinearVertices_-_changes
1.4.LinearizeNear-CollinearVertices_-_polygons: Inspector [off]
1.4.LinearizeNear-CollinearVertices_-_changes: Inspector [off]

Bookmark: 1.5.MovePolygonOriginMostRightAngleVertex
PolygonOriginIdentifier
    ID.POLYGON = @Value(_id.object)
    -> PolygonOriginSetter
    Origins -> PolygonOriginSetter [Origins]
PolygonOriginSetter
    _ID.OBJECT = @Value(_id.object)
    -> 1.5.MovePolygonOriginMostRightAngleVertex
    -> MeasureRemover
    -> AttributeRemover_9
1.5.MovePolygonOriginMostRightAngleVertex: Inspector [off]

Bookmark: 5.1.OriginalNodesRetriever
Note: Result: The vertices of pre-processed polygons are retrieves in their original order.
Chopper_4
    DEAGGREGATE_INPUT = Deaggregate
    MAX_VERTICES = 1
    MODE = By Vertex
    CHOPPED -> Counter_6
    UNTOUCHED -> Counter_6
Counter_6
    CNT_ATTR = _id.node
    DOMAIN = @Value(_id.object)
    SCOPE = Local
    START = 0
    -> Matcher_3

Bookmark: 2.1.AngularTypeIdentification
AttributeRemover_9
    REMOVE_ATTRS = _id.partOf
    -> VertexAngularCalculator_3
VertexAngularCalculator_3
    MEASURE_NAME = AngularChange
    Measures -> AngularChangeLocator
AngularChangeLocator
    MaxCollinearAngleError = $(MaxCollinearAngleError)
    MaxOrthogonalAngleError = $(MaxOrthogonalAngleError)
    -> GeometryCoercer_2
    -> 2.1.PolygonSegmentation-Polygons
    Changes -> Matcher
2.1.PolygonSegmentation-Polygons: Inspector [off]
Matcher
    BLANK_AND_MISSING_DIFFER = No
    CNT_ATTR = _match_id
    LENIENT_MATCH = No
    MATCH = 2D
    MATCH_STRATEGY = Match Selected Attributes
    SINGLE_MATCHED -> Cloner
    NOT_MATCHED -> Cloner
Cloner
    COPIES = 1
    COPY -> 2.1.PolygonSegmentation-Changes
    COPY -> PointOnLineOverlayer_3 [POINT]
2.1.PolygonSegmentation-Changes: Inspector [off]

Bookmark: 2.2.PolygonSegmentation
GeometryCoercer_2
    GQUERY:
      for $geom in //geometry
      where $geom/count(parent::geometry) = 0
      return number($geom/@fme_id)
    KIND = fme_line
    COERCED -> PointOnLineOverlayer_3 [LINE]
PointOnLineOverlayer_3
    DEAGGREGATE_INPUT = Yes
    OV_ATTR = _segmentations
    TOLERANCE = 0
    POINT -> SectionTopology [Changes]
    LINE -> Intersector_2
Intersector_2
    ATTRS_ACCUM_MODE = Use Attributes From One Feature
    CLEANING_TOLERANCE = None
    DEAGGREGATE_INPUT = Yes
    DUPLICATE_Z_NODES = No
    GENERATE_LIST_DROP = NO
    MEASURE_TYPE = Discrete
    NODE_NUM_ATTR = _node_number
    OV_ATTR = _overlaps
    PERFORM_SELF_INTERSECTION = No
    SEG_ATTR = _segments
    SEPARATE_COLLINEAR_SEGMENTS = Yes
    INTERSECTED -> MeasureExtractor_2
MeasureExtractor_2
    GEOM_TYPE = Whole Line
    MEASURE_LIST = _angularType
    MEASURE_NAME = AngularType
    -> Matcher_4
Matcher_4
    BLANK_AND_MISSING_DIFFER = No
    CNT_ATTR = _overlaps_id
    LENIENT_MATCH = Yes
    LIST_ATTRS_TO_INCLUDE = _angularType.origin _angularType{} _id.aggregate _id.object
    MATCH = 2D
    MATCH_STRATEGY = Match Selected Attributes
    SM_LIST_NAME = _overlaps
    MATCHED -> ListRangeExtractor_4
    NOT_MATCHED -> AttributeCreator_4
AttributeCreator_4
    ATTR_TABLE = SET_TO _overlaps_id = @Evaluate(@Count(unmatched,1)*(-1))
    -> ListRangeExtractor_4
ListRangeExtractor_4
    MAX = _angularType.max
    MIN = _angularType.min
    SRC_LIST = _angularType{}
    -> StatisticsCalculator_2
StatisticsCalculator_2
    COMPUTE_HISTOGRAM = NO
    GROUP_BY = _overlaps_id
    MIN_ATTR = _section.angularType
    PREPEND_ATTR_NAME_CHOICE = For multiple results only
    STATS_ATTRS = _angularType.min
    COMPLETE -> AttributeRemover_8
AttributeRemover_8
    LIST_ATTRS = _angularType{}
    REMOVE_ATTRS = _angularType.max,_angularType.origin,_overlaps,_overlaps_id,_angularType.min,_segments,_segmentations
    -> SectionTopology
    -> 2.2.PolygonSegmentation
2.2.PolygonSegmentation: Inspector [off]

Bookmark: 2.3.LinestringsAngularTypeTopology
SectionTopology
    ANGULARTYPE = @Value(_section.angularType)
    NETWORK_ID = _id.section
    -> LinestringsCleaner
    -> 2.3.LinestringsAngularTypeTopology
2.3.LinestringsAngularTypeTopology: Inspector [off]

Bookmark: 3.1.LinestringsCleaner
LinestringsCleaner
    MaxCollinearAngleError = $(MaxCollinearAngleError)
    MaxOrthogonalAngleError = $(MaxOrthogonalAngleError)
    SectionAngularType = @Value(_section.angularType)
    -> 3.1.LinestringsCleaner
    -> Chopper_2
    Removed -> 3.1.LinestringsCleaner-Removed
3.1.LinestringsCleaner: Inspector [off]
3.1.LinestringsCleaner-Removed: Inspector [off]

Bookmark: 3.2.OriginalSegmentCharacteristics
Chopper_2
    DEAGGREGATE_INPUT = Deaggregate
    MAX_VERTICES = 2
    MODE = By Vertex
    CHOPPED -> CoordinateExtractorSegment
    UNTOUCHED -> CoordinateExtractorSegment
CoordinateExtractorSegment
    LIST_NAME = _vertex
    MODE = All Coordinates
    -> AttributeCreatorSegment
AttributeCreatorSegment
    ATTR_TABLE:
      SET_TO _segment.length = @Evaluate(@Length())
      SET_TO _segment.cx = @Evaluate(@average(@Value(_vertex{0}.x),@Value(_vertex{1}.x)))
      SET_TO _segment.cy = @Evaluate(@average(@Value(_vertex{0}.y),@Value(_vertex{1}.y)))
      SET_TO _segment.dx = @Evaluate((@Value(_vertex{1}.x)-@Value(_vertex{0}.x))/@Value(_segment.length))
      SET_TO _segment.dy = @Evaluate((@Value(_vertex{1}.y)-@Value(_vertex{0}.y))/@Value(_segment.length))
      SET_TO _segment.slope = @Evaluate(@Value(_segment.dx)==0.0 ? @real32(2e+32) : @Value(_segment.dy)/@Value(_segment.dx))
      SET_TO _segment.slopeSign = @Evaluate(@Value(_segment.slope)==0.0 ? 1 : @Value(_segment.slope)/abs(@Value(_segment.slope)))
      SET_TO _segment.angle00 = @Evaluate(@atan(@Value(_segment.slope))/@pi()*180)
      SET_TO _segment.angle90 = @Evaluate(@atan(-1/@Value(_segment.slope))/@pi()*180)
      SET_TO _segment.dx = @Evaluate(@abs(@Value(_segment.dx)))
      SET_TO _segment.dy = @Evaluate(@abs(@Value(_segment.dy))*@Value(_segment.slopeSign))
    -> AttributeKeeper_5
AttributeKeeper_5
    KEEP_ATTRS = _section.angularType,_segment.angle90,_segment.dy,_segment.dx,_segment.length,_id.section,_segment.cx,_segment.angle00,_segment.cy,_id.aggregate,_segment.slope,_id.object
    -> Tester_Orthogonal_3
    -> 3.2.OriginalSegmentCharacteristics
3.2.OriginalSegmentCharacteristics: Inspector [off]

Bookmark: 3.3.StandardizedOrthogonalSegmentsCharacteristics
Note: Result: characteristics of segments that belong to an orthogonal section are generalized to obtain representative and uniform values (A,B) for each segment equation Ax+By+C=0 over each aggregate or over a section if not possible. Representativeness is based on the longest segment of each section because shorter segments tend to have higher variations of orientations (angles) in their representation.
Note: Before further processing, orthogonal/non-orthogonal segments are split apart.
Tester_Orthogonal_3
    BOOL_OP = OR
    TEST_CLAUSE = TEST @Value(_section.angularType) = 0
    TEST_MODE = TEST
    PASSED -> StatisticsCalculator
    FAILED -> AttributeCreatorWorkingAngle_3
AttributeCreatorWorkingAngle_3
    ATTR_TABLE:
      SET_TO _segment.standardized.angle = @Value(_segment.angle00)
      SET_TO _section.angularType = 3
    -> AttributeKeeper_15
AttributeKeeper_15
    KEEP_ATTRS = _id.aggregate,_segment.standardized.angle,_id.object,_segment.cx,_id.section,_segment.cy,_section.angularType
    -> 3.3.StandardizedOrthogonalSegmentsCharacteristics
    -> NetworkTopologyCalculator [LINE]
3.3.StandardizedOrthogonalSegmentsCharacteristics: Inspector [off]

Bookmark: 3.3.1. Compute Reference Direction (dx, dy) By Section
StatisticsCalculator
    COMPUTE_HISTOGRAM = NO
    GROUP_BY = _id.section
    MAX_ATTR = _section.length.max
    PREPEND_ATTR_NAME_CHOICE = For multiple results only
    STATS_ATTRS = _segment.length
    SUM_ATTR = _section.length.sum
    COMPLETE -> FeatureJoiner_2 [LEFT]
    COMPLETE -> Tester.SectionLengthMax
Tester.SectionLengthMax
    BOOL_OP = OR
    TEST_CLAUSE = TEST @Value(_segment.length) = @Value(_section.length.max)
    TEST_MODE = TEST
    PASSED -> DuplicateFilter.Section
DuplicateFilter.Section
    INPUT_ORDERED_CHOICE = No
    KEYATTR = _id.section
    UNIQUE -> AttributeRenamer.SectionReference
AttributeRenamer.SectionReference
    ATTR_TABLE:
      RENAME_SET_DEFAULT _segment.dx > _reference.dx.section
      RENAME_SET_DEFAULT _segment.dy > _reference.dy.section
    -> AttributeKeeper_12
Note: Reference dx, dy based on longest segment/section
AttributeKeeper_12
    KEEP_ATTRS = _reference.dx.section,_reference.dy.section,_id.section
    -> FeatureJoiner_2 [RIGHT]
FeatureJoiner_2
    ATTR_CONFLICT_RES = Use Left
    GEOMETRY_HANDLING = Use Left
    JOIN_KEYS = _id.section _id.section AUTO
    JOIN_MODE = Left
    JOINED -> StatisticsCalculator_3
    JOINED -> 3.3.1.ReferenceSectionDxy
3.3.1.ReferenceSectionDxy: Inspector [off]

Bookmark: 3.3.2. Compute Reference (dx, dy) By Aggregate
StatisticsCalculator_3
    COMPUTE_HISTOGRAM = NO
    GROUP_BY = _id.aggregate
    MAX_ATTR = _aggregate.length.max
    PREPEND_ATTR_NAME_CHOICE = For multiple results only
    STATS_ATTRS = _section.length.sum
    COMPLETE -> FeatureJoiner_3 [LEFT]
    COMPLETE -> Tester.AggregateLengthMax
Tester.AggregateLengthMax
    BOOL_OP = OR
    TEST_CLAUSE = TEST @Value(_section.length.sum) = @Value(_aggregate.length.max)
    TEST_MODE = TEST
    PASSED -> DuplicateFilter.Aggregate
DuplicateFilter.Aggregate
    INPUT_ORDERED_CHOICE = No
    KEYATTR = _id.aggregate
    UNIQUE -> AttributeRenamer_4
AttributeRenamer_4
    ATTR_TABLE:
      RENAME_SET_DEFAULT _reference.dx.section > _reference.dx.aggregate
      RENAME_SET_DEFAULT _reference.dy.section > _reference.dy.aggregate
    -> AttributeKeeper_13
Note: Reference dx, dy based on longest section/aggregate
AttributeKeeper_13
    KEEP_ATTRS = _section.angularType,_reference.dx.aggregate,_reference.dy.aggregate,_id.aggregate
    -> FeatureJoiner_3 [RIGHT]
FeatureJoiner_3
    ATTR_CONFLICT_RES = Use Left
    GEOMETRY_HANDLING = Use Left
    JOIN_KEYS = _id.aggregate _id.aggregate AUTO
    JOIN_MODE = Left
    JOINED -> AttributeCreator.SegmentReference_2
    JOINED -> AttributeKeeper_14
    JOINED -> 3.3.2.ReferenceAggregateDxy
3.3.2.ReferenceAggregateDxy: Inspector [off]

Bookmark: 3.3.3. Associate Best Reference Direction (dx, dy) to segments
Note: Associate the most representative reference (dx,dy) to each segment. Priority is given to aggregate’s reference, which should typically be the case, unless some sections’ orientation differs from the aggregate by more than λ. In this case, section’s reference (dx,dy) is used instead.
AttributeKeeper_14
    KEEP_ATTRS = _segment.angle90,_segment.dy,_segment.dx,_segment.length,_segment.slopeSign,_id.section,_segment.cx,_segment.angle00,_segment.cy,_id.aggregate,_segment.slope,_id.object
    -> FeatureMerger_4 [REQUESTOR]
AttributeCreator.SegmentReference_2
    ATTR_TABLE = SET_TO _reference.deltaDirection = @Evaluate(@sqrt(@pow(@Value(_reference.dx.aggregate)-@Value(_reference.dx.section),2)+@pow(@Value(_reference.dy.aggregate)-@Value(_reference.dy.section),2)))
    -> ListBuilder
ListBuilder
    GROUPS_ORDERED = No
    GROUP_BY = _id.aggregate
    LIST_ATTRS_TO_INCLUDE = _id.aggregate _id.section _reference.deltaDirection _reference.dx.aggregate _reference.dx.section _reference.dy.aggregate _reference.dy.section
    LIST_NAME = _sections
    -> ReferenceDxDy
ReferenceDxDy: DxyReferenceMatcher
    DELTA.DIRECTION.MAX = $(MaxOrthogonalAngleError)
    ID.AGGREGATE = @Value(_id.aggregate)
    -> FeatureMerger_4 [SUPPLIER]
FeatureMerger_4
    ATTR_ACCUM_MODE = Merge Supplier
    ATTR_CONFLICT_RES = Use Supplier
    CLEANING_TOLERANCE = None
    CONNECT_Z_MODE = First Wins
    GEOM_TYPE = Build Polygons
    IGNORE_NULLS = No
    JOIN_KEYS = @Value(_id.section) @Value(_id.section) AUTO
    MERGE_TYPE = Attributes Only
    PROCESS_DUPS = YES
    REJECT_NULL_MISSING_KEYS = No
    SUPPLIERS_FIRST = No
    MERGED -> AttributeCreator

Bookmark: Weighted average (dx,dy)
AttributeCreator
    ATTR_TABLE:
      SET_TO _segment.distance2reference.max = @Evaluate(@sqrt(2)/2)
      SET_TO _segment.distance2reference = @Evaluate(@sqrt(@pow(@Value(_reference.dx)-@Value(_segment.dx),2)+@pow(@Value(_reference.dy)-@Value(_segment.dy),2)))
      SET_TO _segment.rotation = @Evaluate(@Value(_segment.distance2reference)>@Value(_segment.distance2reference.max))
      SET_TO _segment.dx.standardized = @Evaluate(@Value(_segment.rotation) ? @abs(@Value(_segment.dy))* @int(@abs(@Value(_reference.dx))/@Value(_reference.dx)) : @Value(_segment.dx))
      SET_TO _segment.dy.standardized = @Evaluate(@Value(_segment.rotation) ? @abs(@Value(_segment.dx))* @int(@abs(@Value(_reference.dy))/@Value(_reference.dy)) : @Value(_segment.dy))
      SET_TO _segment.dx.weighted = @Evaluate(@Value(_segment.dx.standardized)*@Value(_segment.length))
      SET_TO _segment.dy.weighted = @Evaluate(@Value(_segment.dy.standardized)*@Value(_segment.length))
      SET_TO _section.angularType = 0
    -> StatisticsCalculator.Aggregate_2
StatisticsCalculator.Aggregate_2
    COMPUTE_HISTOGRAM = NO
    GROUP_BY = _reference.id _id.aggregate
    PREPEND_ATTR_NAME_CHOICE = For all results
    STATS_ATTRS = _segment.dy.weighted _segment.dx.weighted _segment.length
    SUM_ATTR = sum
    COMPLETE -> AttributeCreator.Section_2
AttributeCreator.Section_2
    ATTR_TABLE:
      SET_TO _segment.standardized.dx = @Evaluate(@Value(_segment.dx.weighted.sum)/@Value(_segment.length.sum))
      SET_TO _segment.standardized.dy = @Evaluate(@Value(_segment.dy.weighted.sum)/@Value(_segment.length.sum))
      SET_TO _segment.standardized.slope = @Evaluate(@Value(_segment.standardized.dx)==0 ? @real32(2e+32) : @Value(_segment.standardized.dy)/@Value(_segment.standardized.dx))
      SET_TO _segment.standardized.angle00 = @Evaluate(@atan(@Value(_segment.standardized.slope))/@pi()*180)
      SET_TO _segment.standardized.angle90 = @Evaluate(@atan(-1/@Value(_segment.standardized.slope))/@pi()*180)
      SET_TO _segment.standardized.angle = @Evaluate(@Value(_segment.rotation) ?  @Value(_segment.standardized.angle90) : @Value(_segment.standardized.angle00))
    -> AttributeKeeper_15
    -> 3.3.3.AssociateReferenceCharacteristics_Segment
3.3.3.AssociateReferenceCharacteristics_Segment: Inspector [off]

Bookmark: 3.4.StandardSegmentEquations(ABC)
NetworkTopologyCalculator
    GROUP_BY = _segment.standardized.angle
    NETWORK_ID_ATTR = _id.segment
    NETWORK -> StatisticsCalculator_5
StatisticsCalculator_5
    COMPUTE_HISTOGRAM = NO
    GROUP_BY = _id.segment
    MEAN_ATTR = mean
    PREPEND_ATTR_NAME_CHOICE = For all results
    STATS_ATTRS = _segment.cy _segment.cx
    COMPLETE -> AttributeCreatorWorkingAngle
AttributeCreatorWorkingAngle
    ATTR_TABLE:
      SET_TO _standardEquation.theta = @Value(_segment.standardized.angle)
      SET_TO _standardEquation.dx = @Evaluate(@cos(@Value(_standardEquation.theta)/180.0*@pi()))
      SET_TO _standardEquation.dy = @Evaluate(@sin(@Value(_standardEquation.theta)/180.0*@pi()))
      SET_TO _standardEquation.cx = @Value(_segment.cx.mean)
      SET_TO _standardEquation.cy = @Value(_segment.cy.mean)
    -> AttributeKeeper
AttributeKeeper
    KEEP_ATTRS = _standardEquation.dy,_standardEquation.theta,_id.section,_standardEquation.cx,_id.object,_standardEquation.dx,_standardEquation.cy,_id.aggregate,_section.angularType
    -> StandardEquationBuilder_2
StandardEquationBuilder_2: AttributeCreator
    ATTR_TABLE:
      SET_TO _standardEquation.A = @Evaluate(@round(@Value(_standardEquation.dy),15)*(-1))
      SET_TO _standardEquation.B = @Evaluate(@round(@Value(_standardEquation.dx),15))
      SET_TO _standardEquation.C = @Evaluate(@round((@Value(_standardEquation.A)*@Value(_standardEquation.cx) + @Value(_standardEquation.B)*@Value(_standardEquation.cy)),15)*(-1))
      SET_TO Proof = @Evaluate(@Value(_standardEquation.A)*@Value(_standardEquation.cx)+@Value(_standardEquation.B)*@Value(_standardEquation.cy)+@Value(_standardEquation.C))
    -> AttributeKeeper_9
AttributeKeeper_9
    KEEP_ATTRS = _standardEquation.dy,_standardEquation.theta,_id.section,_standardEquation.cx,_id.object,_standardEquation.dx,_standardEquation.cy,_standardEquation.B,_id.aggregate,_standardEquation.C,_section.angularType,_standardEquation.A
    -> FeatureMerger_5 [REQUESTOR]
    -> ListBuilder_C
    -> 3.4.StandardSegmentEquations.AB
Note: Result: The expected equation (Ax+By+C) of each segment (orthogonalized or not) is defined.
3.4.StandardSegmentEquations.AB: Inspector [off]

Bookmark: EquationGeneralization(C)
ListBuilder_C
    GROUPS_ORDERED = No
    GROUP_BY = _standardEquation.B _id.aggregate _standardEquation.A
    LIST_ATTRS_TO_INCLUDE = _standardEquation.C
    LIST_NAME = _list
    -> GeneralizeCvalues
GeneralizeCvalues
    DISTANCE.MAX = $(MinOrthogonalSegmentLength)
    STANDARDEQUATION.A = @Value(_standardEquation.A)
    STANDARDEQUATION.B = @Value(_standardEquation.B)
    -> StatisticsCalculator_4
StatisticsCalculator_4
    COMPUTE_HISTOGRAM = NO
    GROUP_BY = _standardEquation.B _group.id _id.aggregate _standardEquation.A
    MEAN_ATTR = mean
    NUMERIC_ATTR = count
    PREPEND_ATTR_NAME_CHOICE = For all results
    STATS_ATTRS = _standardEquation.C
    COMPLETE -> FeatureMerger_5 [SUPPLIER]
FeatureMerger_5
    ATTR_ACCUM_MODE = Merge Supplier
    ATTR_CONFLICT_RES = Use Supplier
    CLEANING_TOLERANCE = None
    CONNECT_Z_MODE = First Wins
    GEOM_TYPE = Build Polygons
    GROUP_BY = _id.aggregate
    IGNORE_NULLS = No
    JOIN_KEYS = @Value(_standardEquation.A) @Value(_standardEquation.A) AUTO @Value(_standardEquation.B) @Value(_standardEquation.B) AUTO @Value(_standardEquation.C) @Value(_standardEquation.C) AUTO
    MERGE_TYPE = Attributes Only
    PROCESS_DUPS = YES
    REJECT_NULL_MISSING_KEYS = No
    SUPPLIERS_FIRST = No
    MERGED -> StandardEquationC
StandardEquationC: AttributeCreator
    ATTR_TABLE = SET_TO _standardEquation.C = @Value(_standardEquation.C.mean)
    -> AttributeKeeper_2
AttributeKeeper_2
    KEEP_ATTRS = _standardEquation.A,_standardEquation.C,_id.object,_standardEquation.B,_id.aggregate,_section.angularType,_id.section
    -> AttributeRenamer
AttributeRenamer
    ATTR_TABLE:
      RENAME_SET_DEFAULT _standardEquation.A > A
      RENAME_SET_DEFAULT _standardEquation.B > B
      RENAME_SET_DEFAULT _standardEquation.C > C
      RENAME_SET_DEFAULT _section.angularType > _angularType
    -> Chopper_3
    -> NeighborFinder_2 [CANDIDATE]
    -> 3.4.StandardSegmentEquations.ABC
Note: Generalize new C values to insure segments are collinear within the threshold ɛ
3.4.StandardSegmentEquations.ABC: Inspector [off]

Bookmark: 4.1.TransferEquations2Node
Chopper_3
    DEAGGREGATE_INPUT = Deaggregate
    MAX_VERTICES = 1
    MODE = By Vertex
    CHOPPED -> MeasureExtractor
    UNTOUCHED -> MeasureExtractor
MeasureExtractor
    GEOM_TYPE = Point
    MEASURE_ATTR = _angularChange
    MEASURE_NAME = AngularChange
    -> AttributeManager
AttributeManager
    ATTR_TABLE:
      SET_TO _angularChange = @Evaluate(@abs(@Value(_angularChange)))
      REMOVE A
      REMOVE B
      REMOVE C
      REMOVE _id.section
      REMOVE _id.aggregate
      REMOVE _angularType
    -> Matcher_2
Matcher_2
    BLANK_AND_MISSING_DIFFER = No
    CNT_ATTR = _id.MatchedNodes
    LENIENT_MATCH = No
    LIST_ATTRS_TO_INCLUDE = _angularChange _id.object
    MATCH = 2D
    MATCH_STRATEGY = Match Selected Attributes
    SM_LIST_NAME = MatchedNodes
    SINGLE_MATCHED -> ListDuplicateRemover
ListDuplicateRemover
    SRC_LIST = MatchedNodes{}._id.object
    -> NeighborFinder_2 [BASE]
NeighborFinder_2
    CANDIDATES_FIRST = No
    CLOSE_LIST_ATTRS_TO_INCLUDE = A B C _angularType _id.object
    CLOSE_LIST_ATTRS_TO_INCLUDE_MODE = Selected Attributes
    CLOSE_LIST_NAME = AdjacentSegments
    INSERT_VERTEX = No
    MAX = 0
    MEASURES_FROM_CANDIDATE = No
    MODE = Bases and Candidates
    TREAT_POLYGON_AS = Lines
    MATCHED -> AttributeKeeper_3
AttributeKeeper_3
    KEEP_ATTRS = _id.MatchedNodes
    KEEP_LIST = AdjacentSegments{}.A AdjacentSegments{}.B AdjacentSegments{}.C AdjacentSegments{}._angularType AdjacentSegments{}._id.object MatchedNodes{}._angularChange MatchedNodes{}._id.object
    -> 4.1.TransferEquations2Node
    -> ListRangeExtractor
4.1.TransferEquations2Node: Inspector [off]

Bookmark: 4.2.TopologicalNodes
Note: Result: Required topological information for later filtering is available. / Required information is: the node may be eventually be removed (node.collinearCleaning [true,false]) and the node belongs to an orthogonal section (node.orthogonalSection [true,false] ).
ListRangeExtractor
    MAX = _angularChange.max
    MIN = _angularChange.min
    SRC_LIST = MatchedNodes{}._angularChange
    -> Tester_collinearCleaning
Tester_collinearCleaning
    BOOL_OP = OR
    TEST_CLAUSE = TEST @Value(_angularChange.min) = @Value(_angularChange.max)
    TEST_MODE = TEST
    PASSED -> ListRangeExtractor_2
    FAILED -> ListRangeExtractor_2
ListRangeExtractor_2
    MAX = _angularType.max
    MIN = _angularType.min
    SRC_LIST = AdjacentSegments{}._angularType
    -> Tester_Orthogonal
Tester_Orthogonal
    BOOL_OP = OR
    TEST_CLAUSE = TEST @Value(_angularType.min) = 0
    TEST_MODE = TEST
    PASSED -> AttributeRemover_2
    FAILED -> AttributeRemover_2
AttributeRemover_2
    REMOVE_ATTRS = _angularChange.min,_angularType.max,_angularChange.max,_angularType.min
    -> ListElementFilter_2
    -> 4.2.TopologicalNodes
4.2.TopologicalNodes: Inspector [off]

Bookmark: 4.3.NewCoordinatesCalculation
ListElementFilter_2
    CASE = No
    EXP = 0
    FILTER_TYPE = EXACT_MATCH
    LIST_ATTR = AdjacentSegments{}._angularType
    NEGATE = No
    Filtered -> AttributeKeeper_8
    NotFound -> AttributeCreator_8
AttributeKeeper_8
    KEEP_ATTRS = _node.collinearCleaning,_node.orthogonalSection
    KEEP_LIST = AdjacentSegments{}.A AdjacentSegments{}.B AdjacentSegments{}.C AdjacentSegments{}._id.object MatchedNodes{}._angularChange MatchedNodes{}._id.object
    -> ListDuplicateRemover_4
ListDuplicateRemover_4
    SRC_LIST = AdjacentSegments{}.C
    -> Tester_NonCollinear_2
Tester_NonCollinear_2
    BOOL_OP = COMPOSITE
    COMPOSITE_TEST = 1 AND (2 OR 3)
    TEST_CLAUSE:
      TEST AdjacentSegments{1}.C ATTRIBUTE_HAS_A_VALUE ""
      TEST @Evaluate(@Value(AdjacentSegments{1}.B)) != @Evaluate(@Value(AdjacentSegments{0}.B))
      TEST @Evaluate(@Value(AdjacentSegments{1}.A)) != @Evaluate(@Value(AdjacentSegments{0}.A))
    TEST_MODE = TEST
    PASSED -> AttributeCreator_11
    FAILED -> StandardEquationBuilder_4
StandardEquationBuilder_4: AttributeCreator
    ATTR_TABLE:
      SET_TO x = @Evaluate(@XValue())
      SET_TO y = @Evaluate(@YValue())
      SET_TO AdjacentSegments{1}.A = @Evaluate(@Value(AdjacentSegments{0}.B)*(-1))
      SET_TO AdjacentSegments{1}.B = @Evaluate(@Value(AdjacentSegments{0}.A))
      SET_TO AdjacentSegments{1}.C = @Evaluate(-(@Value(AdjacentSegments{1}.A)*@Value(x) + @Value(AdjacentSegments{1}.B)*@Value(y)))
      SET_TO _standardEquation.Proof = @Evaluate(@Value(AdjacentSegments{1}.A)*@Value(x) + @Value(AdjacentSegments{1}.B)*@Value(y) + @Value(AdjacentSegments{1}.C))
    -> AttributeCreator_11
Note: HomogeneousCoordinates
AttributeCreator_11
    ATTR_TABLE:
      SET_TO _segmentsEquation.X = @Evaluate(@Value(AdjacentSegments{0}.B)*@Value(AdjacentSegments{1}.C) - @Value(AdjacentSegments{1}.B)*@Value(AdjacentSegments{0}.C))
      SET_TO _segmentsEquation.Y = @Evaluate(@Value(AdjacentSegments{1}.A)*@Value(AdjacentSegments{0}.C) - @Value(AdjacentSegments{0}.A)*@Value(AdjacentSegments{1}.C))
      SET_TO _segmentsEquation.W = @Evaluate(@Value(AdjacentSegments{0}.A)*@Value(AdjacentSegments{1}.B) - @Value(AdjacentSegments{1}.A)*@Value(AdjacentSegments{0}.B))
      SET_TO _node.newX = @Evaluate(@Value(_segmentsEquation.W)==0 ? "NA" : @Value(_segmentsEquation.X)/@Value(_segmentsEquation.W))
      SET_TO _node.newY = @Evaluate(@Value(_segmentsEquation.W)==0 ? "NA" : @Value(_segmentsEquation.Y)/@Value(_segmentsEquation.W))
    -> AttributeKeeper_11
AttributeCreator_8
    ATTR_TABLE:
      SET_TO _node.newX = @Evaluate(@XValue())
      SET_TO _node.newY = @Evaluate(@YValue())
    -> AttributeKeeper_11
AttributeKeeper_11
    KEEP_ATTRS = _node.orthogonalSection,_node.collinearCleaning,_node.newY,_node.newX
    KEEP_LIST = MatchedNodes{}._angularChange MatchedNodes{}._id.object
    -> ListExploder_3
    -> 4.3.NewCoordinatesCalculation
4.3.NewCoordinatesCalculation: Inspector [off]

Bookmark: 5.2.CollinearVerticesRemover
ListExploder_3
    ATTR_ACCUM_MODE = Merge List Attributes
    ATTR_CONFLICT_RES = Use List Attribute Values
    LIST_ATTR = MatchedNodes{}
    ELEMENTS -> Tester_CollinearOrthogonalSection
Tester_CollinearOrthogonalSection
    BOOL_OP = AND
    TEST_CLAUSE:
      TEST @Value(_node.orthogonalSection) = true
      TEST @Value(_node.collinearCleaning) = true
      NUM_TEST @Evaluate(@abs(@Value(_angularChange))) <= $(MaxOrthogonalAngleError)
    TEST_MODE = TEST
    FAILED -> Tester_CollinearNonOrthogonalSection
Tester_CollinearNonOrthogonalSection
    BOOL_OP = AND
    TEST_CLAUSE:
      TEST @Value(_node.orthogonalSection) = false
      TEST @Value(_node.collinearCleaning) = true
      NUM_TEST @Evaluate(@abs(@Value(_angularChange))) <= $(MaxCollinearAngleError)
    TEST_MODE = TEST
    FAILED -> Matcher_3
Matcher_3
    BLANK_AND_MISSING_DIFFER = No
    CNT_ATTR = _id.MatchedNodes
    LENIENT_MATCH = Yes
    LIST_ATTRS_TO_INCLUDE = _id.node _id.object
    MATCH = 2D
    MATCHATTRS = _id.object
    MATCH_STRATEGY = Match Selected Attributes
    SM_LIST_NAME = MatchedNodes
    SINGLE_MATCHED -> ListExploder_2
    NOT_MATCHED -> 5.2.CollinearVertexRemover
5.2.CollinearVertexRemover: Inspector [off]

Bookmark: 5.3.ObjectsReconstruction
ListExploder_2
    ATTR_ACCUM_MODE = Merge List Attributes
    ATTR_CONFLICT_RES = Use List Attribute Values
    INDEX_ATTR = _index.MatchedNodes
    LIST_ATTR = MatchedNodes{}
    ELEMENTS -> VertexCreator
VertexCreator
    MODE_NAME = Replace with Point
    XVAL = @Value(_node.newX)
    YVAL = @Value(_node.newY)
    -> Sorter_3
    <REJECTED> -> 5.3.VertexCreator-Rejected
5.3.VertexCreator-Rejected: Inspector [off]
Sorter_3
    SORT_PARM = _id.object NUMERIC ASCENDING _id.node NUMERIC ASCENDING
    SORTED -> LineBuilder
LineBuilder
    ACCUM_INPUT_ATTRS = Merge Incoming Attributes
    BREAKATTR = _id.object
    REMOVE_DUPLICATES = Yes
    LINE -> 5.3.LineBuilderLine
    POLYGON -> Tester
    POLYGON -> 5.3.LineBuilderPolygon
Tester
    BOOL_OP = OR
    COMPOSITE_TEST = 1
    TEST_CLAUSE = TEST _id.partOf ATTRIBUTE_IS_MISSING ""
    TEST_MODE = TEST
    PASSED -> AttributeKeeper_6
    FAILED -> AttributeCreator_2
AttributeCreator_2
    ATTR_TABLE = SET_TO _id.object = @Value(_id.partOf)
    -> AttributeKeeper_6
AttributeKeeper_6
    KEEP_ATTRS = _id.aggregate,_id.object
    -> DonutBuilder
DonutBuilder
    ALLOW_CYCLES = No
    CONNECT_Z_MODE = First Wins
    DROP = yes
    GROUP_BY = _id.object
    AREA -> VertexAngularCalculator_2
VertexAngularCalculator_2
    MEASURE_NAME = AngularChange
    Measures -> FeatureMerger [REQUESTOR]
    Measures -> 5.3.ObjectReconstruction
    Vertices -> AttributeCreator_6
5.3.ObjectReconstruction: Inspector [off]
5.3.LineBuilderLine: Inspector [off]
5.3.LineBuilderPolygon: Inspector [off]

Bookmark: 5.4.ObjectProcessClassification
AttributeCreator_6
    ATTR_TABLE = SET_TO AngularChange = @Evaluate(@round(@abs(@Value(AngularChange)),5))
    -> ListBuilder_2
ListBuilder_2
    GROUPS_ORDERED = No
    GROUP_BY = _id.object
    LIST_ATTRS_TO_INCLUDE = AngularChange
    LIST_NAME = _object.angularChanges
    -> ListDuplicateRemover_3
ListDuplicateRemover_3
    SRC_LIST = _object.angularChanges{}.AngularChange
    -> ListElementCounter_2
ListElementCounter_2
    CNT_ATTR = _element_count
    LIST_NAME = _object.angularChanges{}
    -> ListSummer
ListSummer
    RESULT = _sum
    SRC_LIST = _object.angularChanges{}.AngularChange
    -> Tester_2
Tester_2
    BOOL_OP = AND
    TEST_CLAUSE:
      TEST @Value(_element_count) <= 2
      TEST @Value(_sum) = 90
    TEST_MODE = TEST
    PASSED -> AttributeKeeper_4
    FAILED -> AttributeKeeper_4
AttributeKeeper_4
    KEEP_ATTRS = _id.object,orthogonalbuilding
    -> FeatureMerger [SUPPLIER]
FeatureMerger
    ATTR_ACCUM_MODE = Merge Supplier
    ATTR_CONFLICT_RES = Use Requestor
    IGNORE_NULLS = No
    JOIN_KEYS = @Value(_id.object) @Value(_id.object) AUTO
    MERGE_TYPE = Attributes Only
    PROCESS_DUPS = NO
    REJECT_NULL_MISSING_KEYS = No
    SUPPLIERS_FIRST = No
    MERGED -> MeasureRemover_3
    MERGED -> Tester_4
Tester_4 [off]
    BOOL_OP = OR
    COMPOSITE_TEST = 1
    TEST_CLAUSE = TEST @Value(orthogonalbuilding) = true
    TEST_MODE = TEST
    PASSED -> 5.4.ObjectProcessClassification.true
    FAILED -> 5.4.ObjectProcessClassification.false
Note: Result: Add an attribute identifying if the polygon was completely orthogonalized or not.
5.4.ObjectProcessClassification.true: Inspector
5.4.ObjectProcessClassification.false: Inspector

Bookmark: 1. FeaturesCleanup&AttributesSetting
Note: Result: Each polygons’ geometry has planar coordinates and a unique identifier (id.object).
Note: Result: Inner and outer polygons stand alone. Each component has a id.object and inner polygons know their outer polygon uuid (id.partOf).
Note: Result: Groups of adjacent buildings (not disjoint) have a same aggregate uuid (id.aggregate). This information is later used to generalize line equations parameters for a same aggregate.
Note: Result: Near-collinear vertices are aligned with each other (resulting angles to adjacent segments are 0). This step helps to keep lines straight in case collinear vertices cannot be removed for topological reasons.

Bookmark: 2.PolygonSegmentationOnAngularChangesClassification
Note: Result: Polygons are converted into linestrings which are split into orthogonal / nonorthogonal segments. Topologically related segments are group into sections, each having a unique identifier (id.section).
Note: Result: Each vertex knows its angular type (orthogonal or not). Locations of changes between orthogonal/non-orthogonal angles are known.
Note: Result: Polygons are split at changes location , if any. Each resulting linestring knows its angular type (orthogonal or not). Superposed linestrings have their angular type made identical, prioritizing orthogonal classification.
Note: Result: Linestrings are grouped into networks of topologically related objects (id.section) according to their angular type (orthogonal or not).

Bookmark: 3.SegmentsCharacteristics
Note: Result: Linestrings are split into individual line segments (2 vertices each) and each segment held its Ax+By+C equation. Line equations are standardized by id.section then by id.aggregate, when the difference between sections are smaller than λ.
Note: Result: Linestrings are split into individual line segments (2 vertices each) and all required segment characteristics to computed line equation is available.
Note: Result: Collinear vertices are removed from linestrings according to threshold ϴ for non-orthogonal segments, and threshold λ for orthogonal ones.

Bookmark: 4.CoordinatesCalculation
Note: Result: Each node (vertex) knows the equations of its adjacent segments, the angular change (angle) and angular type (orthogonal or not) associated to each polygon it belongs to (id.object).
Note: Result: For each node belonging to an orthogonal section, intersection of adjacent lines equation is computed using homogeneous coordinates. Since equations have been settled to be orthogonal, the resulting node coordinate makes adjacent segments orthogonal. For the others, coordinates remain unchanged.

Bookmark: 5.NewPolygonsCreation
Note: Result: The original polygons’ vertices are matched with vertices’ new coordinates without collinear vertices.
Note: Result: The original polygons are rebuilt by using the new coordinates location.

FME custom transformer PolygonOriginSetter

Parameters:
- _ID.OBJECT = @Value(_id.object)   # Id.object

Input (input)
    -> AttributeCreator_4
Origins (input)
    -> AttributeCreator
Output (output)

Bookmark: ExtractVertices
AttributeCreator_4
    ATTR_TABLE = SET_TO _id.vertex.max = @Evaluate(@NumCoords()-1)
    -> Chopper
Chopper
    DEAGGREGATE_INPUT = Deaggregate
    MAX_VERTICES = 1
    MODE = By Vertex
    CHOPPED -> Counter_2
    UNTOUCHED -> Counter_2
Counter_2
    CNT_ATTR = _id.vertex
    DOMAIN = vertices
    SCOPE = Local
    START = 0
    -> Matcher
AttributeCreator
    ATTR_TABLE = SET_TO ObjectOrigin = true
    -> Matcher
Matcher
    BLANK_AND_MISSING_DIFFER = No
    CNT_ATTR = _match_id
    LENIENT_MATCH = No
    MATCH = 2D
    MATCHATTRS = _id.object
    MATCH_STRATEGY = Match Selected Attributes
    SINGLE_MATCHED -> Tester
    NOT_MATCHED -> Tester

Bookmark: ReorderVerticesToMatchNewOrigin
Tester
    BOOL_OP = OR
    TEST_CLAUSE = TEST ObjectOrigin ATTRIBUTE_HAS_A_VALUE ""
    TEST_MODE = TEST
    PASSED -> AttributeCreator_5
    FAILED -> AttributeCreator_7
AttributeCreator_5
    ATTR_TABLE = SET_TO _id.vertex.origine = @Evaluate(@Value(_id.vertex))
    -> StatisticsCalculator
AttributeCreator_7
    ATTR_TABLE:
      SET_TO _id.vertex.origine = -1
      SET_TO ObjectOrigin = false
    -> StatisticsCalculator
StatisticsCalculator
    COMPUTE_HISTOGRAM = NO
    GROUP_BY = _id.object
    MAX_ATTR = _id.vertex.origine
    PREPEND_ATTR_NAME_CHOICE = For multiple results only
    STATS_ATTRS = _id.vertex.origine
    COMPLETE -> AttributeCreator_2
AttributeCreator_2
    ATTR_TABLE = SET_TO _id.vertex.new = @Evaluate(@Value(_id.vertex)-@Value(_id.vertex.origine)>=0 ? @Value(_id.vertex)-@Value(_id.vertex.origine) : @Value(_id.vertex.max)-@Value(_id.vertex.origine)+@Value(_id.vertex))
    -> Tester_3
Tester_3
    BOOL_OP = OR
    TEST_CLAUSE = TEST @Value(ObjectOrigin) = true
    TEST_MODE = TEST
    PASSED -> Sorter_2
    PASSED -> AttributeCreator_3
    FAILED -> Sorter_2
Note: Close the new polygon by duplicating the origin
AttributeCreator_3
    ATTR_TABLE = SET_TO _id.vertex.new = @Value(_id.vertex.max)
    -> Sorter_2

Bookmark: RebuildPolygons
Sorter_2
    SORT_PARM = _id.object NUMERIC ASCENDING _id.vertex.new NUMERIC ASCENDING
    SORTED -> LineBuilder
LineBuilder
    ACCUM_INPUT_ATTRS = Use Attributes From One Feature
    BREAKATTR = _id.object
    REMOVE_DUPLICATES = No
    POLYGON -> AttributeRemover
AttributeRemover
    REMOVE_ATTRS = _id.vertex.new,_id.vertex.origine,ObjectOrigin,_id.vertex.max,_match_id,_id.vertex
    -> Output (output)

FME custom transformer ListElementFilter
Replaces the specified source list with the same name list containing only elements that match the specified condition. If the source list does not contain matched elements at all, the input feature will be output via the NotFound port without any change.
    This transformer performs filtering with one of these filter types.
    ---------- 
    Has Value
    : Every element in the resulting list stores a value (i.e. non-empty, non-null, non-missing).
    Exact Match
    : Every element in the resulting list stores a value that exact matches the specified string.
    Contains
    : Every element in the resulting list stores a value that contains the specified string.
    Begins With
    : Every element in the resulting list stores a value that begins with the specified string.
    Ends With
    : Every element in the resulting list stores a value that ends with the specified string.
    Regular Expression Match
    : Every element in the resulting list stores a value that matches the specified regular expression.
    Numeric Value
    : Every element in the resulting list stores a numeric value.
    Numeric Range
    : Every element in the resulting list stores a numeric value within the specified range.
    ---------- 
    This transformer treats a null and missing element as an empty string when determining if an element matches the filtering condition
    .
    However, a null or missing element will be propagated to the resulting list as is, if it matches the filtering condition.
    This transformer supports simple lists (e.g. _list{}) and structured lists (e.g. _list{}.foo, _list{}.bar), but doesn't support nested lists (e.g. _list{}.sub{}).
    If a member (component) of a structured list is specified as the source, other members (components) of the same list will also be filtered synchronously with the specified member.
    This transformer differentiates a simple list and structured list having the same base name. For example, when "_base{}" is specified as the source, "_base{}.foo" and "_base{}.bar" won't be processed even though the base name is the same as the source list. Vice versa. 
    If the filtering cannot be performed with an unexpected reason (e.g. malformed regular expression), the input feature will be output via the <Rejected> port, and the rejected features will have an attribute named "_rejected_reason" that stores a string describing the rejected reason.
    Example
    Consider that the input feature has this list - contains 5 elements, index range is 0 to 4.
    _list{}.foo = [1,2,3,4,5]
    _list{}.bar = [a,b,c,d,e]
    If you set the parameters like this:
    - Source List Attribute: 
    _list{}.foo
    - Filter Type: 
    Numeric Range
    - Match Expression: 
    (2,5)
    this expression represents "greater than 2 and less than 5"
    the resulting list will be:
    _list{}.foo = [3,4]
    _list{}.bar = [c,d]
    Here, the number of the resulting elements is 2 and the index range is 0 to 1.
Parameters
    Source List Attribute
    :
    Specify a simple list (e.g. _list{}) or a member of a structured list (e.g. _list{}.foo) that should be filtered.
    Fiter Type
    :
    Select one of these filter types.
---------- 
    Has Value
    : Every element in the resulting list stores a value (i.e. non-empty, non-null, non-missing).
    Exact Match
    : Every element in the resulting list stores a value that exact matches the specified string.
    Contains
    : Every element in the resulting list stores a value that contains the specified string.
    Begins With
    : Every element in the resulting list stores a value that begins with the specified string.
    Ends With
    : Every element in the resulting list stores a value that ends with the specified string.
    Regular Expression Match
    : Every element in the resulting list stores a value that matches the specified regular expression.
    Numeric Value
    : Every element in the resulting list stores a numeric value.
    Numeric Range
    : Every element in the resulting list stores a numeric value within the specified range.
---------- 
    Match Expression
    : 
    In the "Exact Match", "Contains", "Begins With", or "Ends With" type filtering, enter a text string as the filtering condition.
    In the "Regular Expression Match" type filtering, enter a regular expression as the filtering condition.
    In the "Numeric Range" type filtering, specify a numeric range as the filtering condition, with this format.
    ---------- 
    ( or [ 
    lower value
    , 
    upper value
    ) or ]
    - Lower value and upper value should be separated by a comma.
    - Blank for the lower/upper value means unlimited.
    - Round bracket ( ) indicates "excluding the specified value"; square bracket [ ] indicates "including the specified value".
    Examples:
    (0,5) matches any numeric value that is greater than 0 and less than 5. 
    (0,5] matches any numeric value that is greater than 0 and less than or equal to 5.
    [0,5) matches any numeric value that is greater than or equal to 0 and less than 5.
    [0,5] matches any numeric value that is greater than or equal to 0 and less than or equal to 5.
    [0,) matches any numeric value that is greater than or equal to 0.
    (,5) matches any numeric value that is less than 5.
    ----------
    This parameter setting does not affect the result of the "Has Value" and "Numeric Value" type filtering.
    Case Sensitive
    :
    By default, the filtering of "Exact Match" or "Regular Expression Match" type will be performed in case-insensitive. If you set "Yes" to this parameter, the filtering will be performed in case-sensitive.
    This parameter setting does not affect the result of the filtering with other types.
    Negate Filtering Condition
    :
    If you set "Yes" to this parameter, this transformer performs the filtering with the negate condition. For example, if you set "[0,5]" to the "Match Expression" in the "Numeric Range" type filtering and then set "Yes" to this parameter, the resulting list will contain elements that are less than 0 or greater than 5.
    Note: the transformer won't select non-numeric elements in the "Numeric Range" type filtering even if you set "Yes" to the "Negate Filtering Condition" parameter.

Parameters:
- LIST_ATTR =   # " " Source List Attribute
- FILTER_TYPE = HAS_VALUE
- EXP =   # Match Expression
- CASE = No   # Case Sensitive
- NEGATE = No   # Negate Filtering Condition

Input (input)
    -> ParameterFetcher
Note: History of the Tcl Script: / 2016-03-27 Original Implementation / 2016-03-28 Added Filtering Types - "CONTAINS", "BEGINS_WITH", "ENDS_WITH"
ParameterFetcher
    ATTR_LIST = __listelementfilter.list_attr {$(LIST_ATTR)} __listelementfilter.filter_type {$(FILTER_TYPE)} __listelementfilter.case {$(CASE)} __listelementfilter.exp {$(EXP)} __listelementfilter.negate {$(NEGATE)}
    -> TclCaller
TclCaller
    SRC:
      proc filterListElements {} {
          set listAttr [FME_GetAttribute "__listelementfilter.list_attr"]
          if {![regexp {^([^{}]+){}(\.[^{}]+)?$}  $listAttr m base suffix]} {
              return "failed interpreting source list name: $listAttr"
          }

          set maxIndex -1
          set suffixes {}
          if {[string equal $suffix {}]} {
              set listAttrPattern "^$base{(\\d+)}()\$"
          } else {
              set listAttrPattern "^$base{(\\d+)}(\\.\[^{}\]+)\$"
          }
          foreach attr [FME_AttributeNames] {
              if {[regexp $listAttrPattern $attr m i s]} {
                  if {$maxIndex < $i} {
                      set maxIndex $i
                  }
                  if {[lsearch $suffixes $s] < 0} {
                      lappend suffixes $s
                  }
              }
          }

          set isNoCase [string equal [FME_GetAttribute "__listelementfilter.case"] "No"]
          if {$isNoCase} {
              set exp [string tolower [FME_GetAttribute "__listelementfilter.exp"]]
          } else {
              set exp [FME_GetAttribute "__listelementfilter.exp"]
          }
          proc attrValue {attr isNoCase} {
              if {$isNoCase} {
                  return [string tolower [FME_GetAttribute $attr]]
              } else {
                  return [FME_GetAttribute $attr]
              }
          }
          proc matchString {s} {
              return [string map {\\ \\\\ * \\* ? \\? \[ \\\[ \] \\\]} $s]
          }

          set indices {}
          set doMatch 0
          set filterType [FME_GetAttribute "__listelementfilter.filter_type"]
          switch  $filterType {
              "HAS_VALUE" {
                  for {set i 0} {$i <= $maxIndex} {incr i} {
                      if {![string equal [FME_GetAttribute "$base{$i}$suffix"] {}]} {
                          lappend indices $i
                      }
                  }
              }
              "EXACT_MATCH" {
                  for {set i 0} {$i <= $maxIndex} {incr i} {
                      if {[string equal $exp [attrValue "$base{$i}$suffix" $isNoCase]]} {
                          lappend indices $i
                      }
                  }
              }
              "CONTAINS" {set exp "*[matchString $exp]*"; set doMatch 1}
              "BEGINS_WITH" {set exp "[matchString $exp]*"; set doMatch 1}
              "ENDS_WITH" {set exp "*[matchString $exp]"; set doMatch 1}
              "REGEX_MATCH" {
                  for {set i 0} {$i <= $maxIndex} {incr i} {
                      if {[catch {regexp $exp [attrValue "$base{$i}$suffix" $isNoCase]} matched]} {
                          return "failed interpreting regular expression: [FME_GetAttribute __listelementfilter.exp]"
                      } elseif {$matched} {
                          lappend indices $i
                      }
                  }
              }
              "NUMERIC_VALUE" {
                  for {set i 0} {$i <= $maxIndex} {incr i} {
                      if {[string is double -strict [FME_GetAttribute "$base{$i}$suffix"]]} {
                          lappend indices $i
                      }
                  }
              }
              "NUMERIC_RANGE" {
                  set exp [string trim [string map {( < [ <= ) < ] <=} $exp]]
                  if {![regexp {^(<=?)\s*(.*)\s*,\s*(.*)\s*(<=?)$}  $exp m op1 lower upper op2] \
                      || !([string is double $lower] && [string is double $upper])} {
                      return "failed interpreting numeric range expression: [FME_GetAttribute __listelementfilter.exp]"
                  }
                  for {set i 0} {$i <= $maxIndex} {incr i} {
                      set value [FME_GetAttribute "$base{$i}$suffix"]
                      if {[string is double -strict $value] \
                          && ([string equal $lower {}] || [expr $lower $op1 $value]) \
                          && ([string equal $upper {}] || [expr $value $op2 $upper])} {
                          lappend indices $i
                      }
                  }
              }
              default {
                  return "debug - undefined filter type: $filterType"
              }
          }
          if {$doMatch} {
              for {set i 0} {$i <= $maxIndex} {incr i} {
                  if {[string match $exp [attrValue "$base{$i}$suffix" $isNoCase]]} {
                      lappend indices $i
                  }
              }
          }

          if {[string equal [FME_GetAttribute "__listelementfilter.negate"] "Yes"]} {
              set t {}
              set indices [lsort $indices]
              if {[string equal $filterType "NUMERIC_RANGE"]} {
                  for {set i 0} {$i <= $maxIndex} {incr i} {
                      if {[lsearch -sorted $indices $i] < 0 \
                          && [string is double -strict [FME_GetAttribute "$base{$i}$suffix"]]} {
                          lappend t $i
                      }
                  }
              } else {
                  for {set i 0} {$i <= $maxIndex} {incr i} {
                      if {[lsearch -sorted $indices $i] < 0} {
                          lappend t $i
                      }
                  }
              }
              set indices $t
          }

          if {0 < [llength $indices]} {
              set index 0
              foreach oldIndex [lsort -integer $indices] {
                  if {$index != $oldIndex} {
                      foreach s $suffixes {
                          set oldName "$base{$oldIndex}$s"
                          if {[FME_AttributeExists $oldName]} {
                              FME_RenameAttribute "$base{$index}$s" $oldName
                          } else {
                              FME_UnsetAttributes "$base{$index}$s"
                          }
                      }
                  }
                  incr index
              }
              while {$index <= $maxIndex} {
                  foreach s $suffixes {
                      FME_UnsetAttributes "$base{$index}$s"
                  }
                  incr index
              }
              return filtered
          } else {
              return not_found
          }
      }
    TCLPROG = filterListElements
    VAL_ATTR = __listelementfilter.result
    -> TestFilter
TestFilter
    DEFAULT_VALUE = <UNFILTERED>
    TEST_LIST = BOOL_OP,OR,COMPOSITE_TEST,<Unused>,TEST_CLAUSE,"TEST @Value(__listelementfilter.result) = filtered",filtered,BOOL_OP,OR,COMPOSITE_TEST,<Unused>,TEST_CLAUSE,"TEST @Value(__listelementfilter.result) = not_found",not_found
    filtered -> Filtered (output)
    not_found -> NotFound (output)
    <UNFILTERED> -> AttributeRenamer
Filtered (output)
NotFound (output)
AttributeRenamer
    ATTR_LIST = __listelementfilter.result,_rejected_reason,
    -> <Rejected> (output)
<Rejected> (output)

FME custom transformer GeneralizeCvalues

Parameters:
- STANDARDEQUATION.B = @Value(_standardEquation.B)   # Line equation parameter (B)
- STANDARDEQUATION.A = @Value(_standardEquation.A)   # Line equation parameter (A)
- DISTANCE.MAX =   # Minimum distance between parallel lines

Input (input)
    -> ListSorter
ListSorter
    ORDER = Ascending
    SRC_LIST = _list{}._standardEquation.C
    TYPE = Numeric
    -> ListElementCounter
ListElementCounter
    CNT_ATTR = Cvalues.elementCount
    LIST_NAME = _list{}
    -> AttributeCreator_3
AttributeCreator_3
    ATTR_TABLE:
      SET_TO _group.index = 0
      SET_TO _group.indexMax = @Evaluate(@Value(Cvalues.elementCount)-1)
      SET_TO _group.id = 0
      SET_TO _group.reference.C = @Value(_list{0}._standardEquation.C)
      SET_TO Distance.max = $(DISTANCE.MAX)
    -> ListIndexer
Loop (input)
    -> ListIndexer
ListIndexer
    INDEX = @Value(_group.index)
    LIST_ATTR = _list{}
    PREFIX = _group.
    -> AttributeCreator_5
AttributeCreator_5
    ATTR_TABLE:
      SET_TO C1 = @Value(_group.reference.C)
      SET_TO C2 = @Value(_group._standardEquation.C)
      SET_TO AB = @Evaluate(@sqrt(@Value(_standardEquation.A)**2 + @Value(_standardEquation.B)**2))
      SET_TO Distance = @Evaluate(@abs(@Value(C1)-@Value(C2)) / @Value(AB))
    -> Tester
Tester
    BOOL_OP = OR
    TEST_CLAUSE = TEST @Value(Distance) > @Value(Distance.max)
    TEST_MODE = TEST
    PASSED -> AttributeCreator_2
    FAILED -> AttributeCreator_4
AttributeCreator_2
    ATTR_TABLE:
      SET_TO _group.id = @Evaluate(@Value(_group.id)+1)
      SET_TO _group.reference.C = @Value(C2)
    -> AttributeCreator_4
Note: Problem: Find the distance between two parallel lines from their equations. / Example: 5x + 3y + 6 = 0 and 5x + 3y – 6 = 0. Solution: A=5, B=3, C1=6 and C2=−6. / distance = |C1–C2| / SQRT(AxA + BxB) / distance = |6−(−6)| / SQRT(5X5+ 3X3) = 12/SQRT(34) = 12/5.831 = 2.058 / Group reference is C1 / https://www.toppr.com/guides/maths/straight-lines/distance-of-point-from-a-line/
AttributeCreator_4
    ATTR_TABLE = SET_TO _group.index = @Evaluate(@Value(_group.index)+1)
    -> Tester_2
Tester_2
    BOOL_OP = OR
    TEST_CLAUSE = TEST @Value(_group.index) > @Value(_group.indexMax)
    TEST_MODE = TEST
    PASSED -> AttributeRenamer
    FAILED -> Loop (output)
    FAILED -> AttributeRenamer
AttributeRenamer
    ATTR_TABLE = RENAME_SET_DEFAULT C2 > _standardEquation.C
    -> AttributeRemover
AttributeRemover
    LIST_ATTRS = _list{}._standardEquation.C
    REMOVE_ATTRS = Distance,Distance.max,_group.index,AB,_group.indexMax,_group.reference.C,_group._standardEquation.C,Cvalues.elementCount,C1
    -> Output (output)
Output (output)
Loop (output)

FME custom transformer LinestringsCleaner

Parameters:
- MaxOrthogonalAngleError = 10   # Maximum error on orthogonal angles (deg)
- MaxCollinearAngleError = 5   # Maximum error on collinear angles (deg)
- SectionAngularType = @Value(_section.angularType)   # Section.angulartype

Input (input)
    -> AttributeCreator
Note: Scan linestring to remove collinear vertices except for first/last coordinates
AttributeCreator
    ATTR_TABLE:
      SET_TO LoopIndex = 1
      SET_TO LoopIndexMax = @Evaluate(@NumCoords()-2)
      SET_TO _index = 1
    -> Tester
Loop (input)
    -> Tester
Tester
    BOOL_OP = OR
    TEST_CLAUSE = TEST @Value(LoopIndex) > @Value(LoopIndexMax)
    TEST_MODE = TEST
    PASSED -> AttributeRemover
    FAILED -> MeasureExtractor_3
AttributeRemover
    REMOVE_ATTRS = index,LoopIndexMax,_num_removed,LoopIndex,_point_measure,_angularChange,LoopMaxIndex,_index
    -> Output (output)
Output (output)
MeasureExtractor_3
    GEOM_TYPE = Individual Vertex by Index
    INDEX = @Value(LoopIndex)
    MEASURE_ATTR = _angularChange
    MEASURE_NAME = AngularChange
    -> Tester_CollinearVertex_2
Tester_CollinearVertex_2
    BOOL_OP = COMPOSITE
    COMPOSITE_TEST = (1 AND 2) OR (3 AND 4)
    TEST_CLAUSE:
      TEST @Value(_section.angularType) = 0
      TEST @Evaluate(@abs(@Value(_angularChange))) <= $(MaxOrthogonalAngleError)
      TEST @Value(_section.angularType) = 3
      TEST @Evaluate(@abs(@Value(_angularChange))) <= $(MaxCollinearAngleError)
    TEST_MODE = TEST
    PASSED -> VertexRemover
    PASSED -> Geometry2Point
    FAILED -> AttributeCreator_4
Geometry2Point
    IND = @Value(LoopIndex)
    -> AttributeRemover_2
AttributeRemover_2
    REMOVE_ATTRS = LoopIndexMax,LoopMaxIndex,LoopIndex,_section.angularType,_num_removed,_point_measure,index
    -> Removed (output)
Removed (output)
VertexRemover
    IND = @Value(LoopIndex)
    KEEP_REMOVE_PARAM = Remove
    LEN = 1
    -> AttributeCreator_4
AttributeCreator_4
    ATTR_TABLE:
      SET_TO LoopIndex = @Evaluate(@Value(LoopIndex)+1)
      SET_TO LoopIndexMax = @Evaluate(@NumCoords()-2)
      SET_TO _index = @Evaluate(@Value(_index)+1)
    -> Loop (output)
Loop (output)

FME custom transformer DxyReferenceMatcher

Parameters:
- DELTA.DIRECTION.MAX = 10.0   # Maximum error on orthogonal angles (deg)
- ID.AGGREGATE = @Value(_id.aggregate)   # Aggregates' unique identifier

Input (input)
    -> ListDuplicateRemover
ListDuplicateRemover
    SRC_LIST = _sections{}._id.section
    -> ListSorter
ListSorter
    ORDER = Ascending
    SRC_LIST = _sections{}._reference.deltaDirection
    TYPE = Numeric
    -> ListElementCounter
ListElementCounter
    CNT_ATTR = Current.MaxIndex
    LIST_NAME = _sections{}
    -> AttributeCreator_0
AttributeCreator_0
    ATTR_TABLE:
      SET_TO _reference.dx = @Evaluate(@real64(@Value(_sections{0}._reference.dx.aggregate)))
      SET_TO _reference.dy = @Evaluate(@real64(@Value(_sections{0}._reference.dy.aggregate)))
      SET_TO _reference.id = @Value(_id.aggregate)
      SET_TO _deltaDirection.max = @Evaluate(@degToRad($(DELTA.DIRECTION.MAX)))
      SET_TO Current.Index = 0
      SET_TO Current.MaxIndex = @Evaluate(@Value(Current.MaxIndex)-1)
    -> ListIndexer
Loop (input)
    -> ListIndexer
ListIndexer
    INDEX = @Value(Current.Index)
    LIST_ATTR = _sections{}
    PREFIX = Current.
    -> AttributeCreator_1
AttributeCreator_1
    ATTR_TABLE:
      SET_TO _id.section = @Value(Current._id.section)
      SET_TO Current._reference.deltaDirection = @Evaluate(@sqrt(@pow(@Value(_reference.dx)-@Value(Current._reference.dx.section),2)+@pow(@Value(_reference.dy)-@Value(Current._reference.dy.section),2)))
    -> TesterDistance
TesterDistance
    BOOL_OP = OR
    TEST_CLAUSE = TEST @Value(Current._reference.deltaDirection) <= @Value(_deltaDirection.max)
    TEST_MODE = TEST
    PASSED -> ListElementFilter
    FAILED -> AttributeCreator_6
Note: Reset references when a section deviates by more than MaxOrthogonalAngleError
AttributeCreator_6
    ATTR_TABLE:
      SET_TO _reference.dx = @Value(_sections{0}._reference.dx.section)
      SET_TO _reference.dy = @Value(_sections{0}._reference.dy.section)
      SET_TO _reference.id = @Evaluate(@Value(_reference.id)+1)
      SET_TO Current.Index = 0
      SET_TO Current.MaxIndex = @Evaluate(@Value(Current.MaxIndex)-1)
    -> ListElementFilter
Note: Each loop drop current section from the list. The process completes when the list is not found anymore
ListElementFilter
    CASE = No
    EXP = @Value(Current._id.section)
    FILTER_TYPE = EXACT_MATCH
    LIST_ATTR = _sections{}._id.section
    NEGATE = Yes
    Filtered -> ListElementCounter_2
    Filtered -> AttributeKeeper
    NotFound -> AttributeKeeper
ListElementCounter_2
    CNT_ATTR = Current.MaxIndex
    LIST_NAME = _aggregate.section{}
    -> AttributeCreator_3
AttributeCreator_3
    ATTR_TABLE:
      SET_TO Current.Index = 0
      SET_TO Current.MaxIndex = @Evaluate(@Value(Current.MaxIndex)-1)
    -> Loop (output)
Loop (output)
AttributeKeeper
    KEEP_ATTRS = _id.section,_reference.dx,_reference.id,_id.aggregate,_reference.dy
    -> Output (output)
Output (output)

FME custom transformer LinearizeSegments

Parameters:
- MaxCollinearAngleError = 2.5   # Maximum error on collinear angles (deg)
- MinOrthogonalSegmentLength = 0.5   # Minimum orthogonal segments length (m)
- _ID.OBJECT = @Value(_id.object)   # Id.object

Input (input)
    -> VertexAngularCalculator
VertexAngularCalculator
    MEASURE_NAME = AngularChange
    Measures -> AnchoredSnapper_2 [CANDIDATE]
    Vertices -> AttributeCreator_2
Output (output)
Changes (output)

Bookmark: CreateStraightenPolygon
AttributeCreator_2
    ATTR_TABLE = SET_TO AngularChange = @Evaluate(@abs(@Value(AngularChange)))
    -> Tester_NonCollinear
Tester_NonCollinear
    BOOL_OP = OR
    TEST_CLAUSE = TEST @Value(AngularChange) <= $(MaxCollinearAngleError)
    TEST_MODE = TEST
    PASSED -> AnchoredSnapper_1 [CANDIDATE]
    FAILED -> LineBuilder
LineBuilder
    ACCUM_INPUT_ATTRS = Use Attributes From One Feature
    BREAKATTR = _id.object
    REMOVE_DUPLICATES = No
    LINE -> LineCloser
    POLYGON -> AttributeKeeper
LineCloser
    CONNECT_Z_MODE = First Wins
    AREA -> AttributeKeeper
AttributeKeeper
    KEEP_ATTRS = _id.object
    -> AnchoredSnapper_1 [ANCHOR]
AnchoredSnapper_1
    CLEANING_TOLERANCE = Automatic
    GROUP_BY = _id.object
    SNAPTYPE_PARAM = Segment Snapping
    TOLERANCE = $(MinOrthogonalSegmentLength)
    SNAPPED -> AnchoredSnapper_2 [ANCHOR]

Bookmark: SnapOriginalGeometrytoStraightenPolygons
AnchoredSnapper_2
    EXTEND_LINES = NEVER
    SNAPTYPE_PARAM = Vertex Snapping
    TOLERANCE = $(MinOrthogonalSegmentLength)
    SNAPPED -> AttributeRemover
    UNTOUCHED -> AttributeRemover
    ANCHORS -> Changes (output)
AttributeRemover
    -> MeasureRemover
MeasureRemover
    REMOVE_ALL = Yes
    -> Output (output)

FME custom transformer Geometry2Point

Parameters:
- IND =   # Coordinate Index

Input (input)
    -> CoordinateExtractor
CoordinateExtractor
    IND = $(IND)
    MODE = Specify Coordinate
    X_ATTR = _x
    Y_ATTR = _y
    Z_ATTR = _z
    -> VertexCreator
VertexCreator
    MODE_NAME = Replace with Point
    XVAL = @Value(_x)
    YVAL = @Value(_y)
    ZVAL = @Value(_z)
    -> AttributeRemover
AttributeRemover
    REMOVE_ATTRS = _x,_z,_y
    -> Output (output)
Output (output)

FME custom transformer PolygonOriginIdentifier

Parameters:
- ID.POLYGON = @Value(_id.object)   # Polygon unique identifier

Input (input)
    -> VertexAngularCalculator
Output (output)
Origins (output)

Bookmark: PolygonOriginIdentifier
Note: Origin set to a vertice with an AngularChange close to 90 degree
VertexAngularCalculator
    MEASURE_NAME = AngularChange
    Measures -> MeasureRemover
    Vertices -> Tester_2
MeasureRemover
    MEASURE_NAME = AngularChange
    REMOVE_ALL = No
    -> Output (output)
Tester_2
    BOOL_OP = OR
    TEST_CLAUSE = TEST @Value(_id.vertex) != 0
    TEST_MODE = TEST
    PASSED -> AttributeCreator
AttributeCreator
    ATTR_TABLE = SET_TO Delta90.value = @Evaluate(@abs(90-@abs(@Value(AngularChange))))
    -> Sorter
Sorter
    SORT_PARM = _id.object NUMERIC ASCENDING Delta90.value NUMERIC ASCENDING
    SORTED -> Counter
Counter
    CNT_ATTR = Delta90.order
    DOMAIN = @Value(_id.object)
    SCOPE = Local
    START = 0
    -> Tester
Tester
    BOOL_OP = OR
    TEST_CLAUSE = TEST @Value(Delta90.order) = 0
    TEST_MODE = TEST
    PASSED -> AttributeRemover
AttributeRemover
    REMOVE_ATTRS = AngularChange,Delta90.order,Delta90.value
    -> Origins (output)

FME custom transformer SectionTopology

Parameters:
- NETWORK_ID =   # Network ID Attribute
- ANGULARTYPE =   # Segment's angular type

Note: Result: Linestrings are grouped into networks of topologically related objects (id.section) according to their angular type (orthogonal or not).
Input (input)
    -> AttributeCreator
AttributeCreator
    ATTR_TABLE:
      SET_TO _angularType = $(ANGULARTYPE)
      SET_TO _snippedSize = 0.0000001
      SET_TO _snippedLoctionF = @Value(_snippedSize)
      SET_TO _snippedLoctionL = @Evaluate(@Length()-@Value(_snippedSize))
    -> Counter
Counter
    CNT_ATTR = _id.segment
    DOMAIN = counter
    SCOPE = Local
    START = 0
    -> Tester_F
    -> FeatureJoiner [LEFT]
Tester_F
    BOOL_OP = OR
    TEST_CLAUSE = TEST @Value(_angularType) = 3
    TEST_MODE = TEST
    PASSED -> NetworkTopologyCalculator_2 [LINE]
    FAILED -> Clipper [CLIPPEE]
Changes (input)
    -> Bufferer
Bufferer
    ANGLE = 22.5
    CAP_STYLE = Round
    CORNER_STYLE = Round
    MODE = AREA
    OFFSET = 0.001
    BUFFERED -> Clipper [CLIPPER]
Clipper
    BOUNDARY_CASES = Treat as Inside
    CLEANING_TOLERANCE = None
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    OUTSIDE -> NetworkTopologyCalculator_2 [LINE]
NetworkTopologyCalculator_2
    GROUP_BY = _angularType
    NETWORK_ID_ATTR = $(NETWORK_ID)
    NETWORK -> FeatureJoiner [RIGHT]
FeatureJoiner
    ATTR_CONFLICT_RES = Use Left
    GEOMETRY_HANDLING = Use Left
    JOIN_KEYS = _id.segment _id.segment AUTO
    JOIN_MODE = Left
    JOINED -> AttributeRemover
AttributeRemover
    REMOVE_ATTRS = _snippedSize,_id.segment,_snippedLoctionL,_angularType,_fme_no_clipper,_snippedLoctionF
    -> Output (output)
Output (output)

FME custom transformer VertexAngularCalculator
This transformer takes as input a line or a polygon and calculates the change of direction (angle) at each vertex.
Transformer inspired from VertexAngleCalculator (VICREA).
Usage
This transformer takes as input a line or a polygon and calculates the change of direction (angle) at each vertex.
The resulting angles are stored in degrees [-180, + 180]. The value is set to 0 for the first and last vertex of an open line. Negative values ​​represent a left turn following the direction of the geometry.
Input Ports
Input: Lines and polygons to be processed.
Output Ports
Measures:  Processed features. Resulting angles stored as a measure on each vertex.
Vertices:  Individual vertices with all original feature attributes. The resulting angle is stored in a variable. A sequential vertex identifier is also provided (_id.vertex). 
Parameters
Destination Measure Name: identifies the name of both the measure and the variable in which the results are stored.
Limitations
The transformer only supports fme_line, fme_polygon and fme_donut geometry.

Parameters:
- MEASURE_NAME = AngularChange   # Destination Measure Name

Note: Measure: Angle between segments / LoopIndex... / C : Current vertex / P : Previous vertex / N : Next vertex / Min : Current ring's origin / Max : Current object's last vertex
Input (input)
    -> MeasureSetter_3
Loop (input)
    -> Tester_LoopStop
Note: loop over all vertices until the last one has been processed
Note: Extract required coordinates / - Current ring origin / - Current vertex / - Previous vertex / - Next vertex
Note: Compute angle between current vertex and adjacent segments by referring to previous and next vertices
Note: Compute anglular change at vertex (i.e. between two vectors) / https://www.wikihow.com/Find-the-Angle-Between-Two-Vectors / Compute direction of the angular change at vertex (i.e. (-) angle turns left, (+) angle turns right / https://gis.stackexchange.com/questions/292370/direction-of-two-lines-turn-right-or-left
Tester_LoopStop
    BOOL_OP = OR
    TEST_CLAUSE = TEST @Value(LoopIndex.C) > @Value(LoopIndex.Max)
    TEST_MODE = TEST
    PASSED -> Counter_ObjectId
    FAILED -> CoordinateExtractor_Origin
Note: Extract each vertices with its angle measurement and a sequential id by object (Counter_ObjectId)
AttributeRemover
    REMOVE_ATTRS = CN.Length,CP.Length,CPr.dx,_vertex.P.x,CN.dx,LoopIndex.Min,LoopIndex.P,PCN.LenProduct,_vertex.C.x,_count,_vertex.P.y,LoopIndex.N,PCN.DotProduct,PCN.deg,AngularChange.Current,_vertex.N.x,LoopIndex.C,_vertex.0.y,PCN.rad,PCNr.DotProduct,LoopClosed.N,SignedDirection,LoopIndex.Max,CN.dy,CPr.dy,_vertex.N.y,PCN.CosAngle,_vertex.0.x,CP.dx,_vertex.C.y,CP.dy
    -> Measures (output)
Measures (output)
Note: Add current angle to measure / If it is a ring (inner or outer), the vertices on both sides of its origin are used to compute the angle and the same value is registered in the measure of first and last coordinates
Vertices (output)
Note: Setup indices for the next loop
Loop (output)

Bookmark: InitializeVariables
MeasureSetter_3
    GEOM_TYPE = All Vertices to Same Value
    MEASURE_NAME = $(MEASURE_NAME)
    MEASURE_VAL = 0.0
    -> AttributeCreator_3
AttributeCreator_3
    ATTR_TABLE:
      SET_TO LoopIndex.Max = @Evaluate(@NumCoords()-1)
      SET_TO LoopIndex.Min = 0
      SET_TO LoopIndex.P = 0
      SET_TO LoopIndex.C = 1
      SET_TO LoopIndex.N = 2
    -> Tester_LoopStop

Bookmark: VerticesGenerator
Counter_ObjectId
    CNT_ATTR = _count
    DOMAIN = counter
    SCOPE = Local
    START = 0
    -> Chopper
    -> AttributeRemover
Chopper
    DEAGGREGATE_INPUT = Deaggregate
    MAX_VERTICES = 1
    MODE = By Vertex
    CHOPPED -> Counter
    UNTOUCHED -> Counter
Counter
    CNT_ATTR = _id.vertex
    DOMAIN = @Value(_count)
    SCOPE = Local
    START = 0
    -> MeasureExtractor_2
MeasureExtractor_2
    GEOM_TYPE = Point
    MEASURE_ATTR = $(MEASURE_NAME)
    MEASURE_NAME = $(MEASURE_NAME)
    -> MeasureRemover
MeasureRemover
    MEASURE_NAME = $(MEASURE_NAME)
    REMOVE_ALL = No
    -> AttributeRemover_2
AttributeRemover_2
    REMOVE_ATTRS = LoopIndex.N,_vertex.P.x,CPr.dx,_vertex.N.y,_vertex.C.x,PCN.rad,AngularChange.Current,CN.dx,LoopIndex.P,_count,LoopIndex.Max,_vertex.0.y,_vertex.C.y,CN.Length,CPr.dy,CP.Length,PCN.DotProduct,_vertex.0.x,PCN.CosAngle,PCN.deg,PCN.LenProduct,_vertex.N.x,LoopClosed.N,LoopIndex.C,LoopIndex.Min,SignedDirection,_vertex.P.y,CP.dx,CN.dy,CP.dy,PCNr.DotProduct
    -> Vertices (output)

Bookmark: Extract required coordinates
CoordinateExtractor_Origin
    IND = @Value(LoopIndex.Min)
    MODE = Specify Coordinate
    X_ATTR = _vertex.0.x
    Y_ATTR = _vertex.0.y
    -> CoordinateExtractor.Previous
CoordinateExtractor.Previous
    IND = @Value(LoopIndex.P)
    MODE = Specify Coordinate
    X_ATTR = _vertex.P.x
    Y_ATTR = _vertex.P.y
    -> CoordinateExtractor.Current
CoordinateExtractor.Current
    IND = @Value(LoopIndex.C)
    MODE = Specify Coordinate
    X_ATTR = _vertex.C.x
    Y_ATTR = _vertex.C.y
    -> CoordinateExtractor.Next
CoordinateExtractor.Next
    IND = @Value(LoopIndex.N)
    MODE = Specify Coordinate
    X_ATTR = _vertex.N.x
    Y_ATTR = _vertex.N.y
    -> AttributeCreator_vectors

Bookmark: ComputeAngularChange
AttributeCreator_vectors
    ATTR_TABLE:
      SET_TO CP.dx = @Evaluate(@Value(_vertex.C.x)-@Value(_vertex.P.x))
      SET_TO CP.dy = @Evaluate(@Value(_vertex.C.y)-@Value(_vertex.P.y))
      SET_TO CP.Length = @Evaluate(@sqrt(@pow(@Value(CP.dx),2)+@pow(@Value(CP.dy),2)))
      SET_TO CN.dx = @Evaluate(@Value(_vertex.N.x)-@Value(_vertex.C.x))
      SET_TO CN.dy = @Evaluate(@Value(_vertex.N.y)-@Value(_vertex.C.y))
      SET_TO CN.Length = @Evaluate(@sqrt(@pow(@Value(CN.dx),2)+@pow(@Value(CN.dy),2)))
    -> AttributeCreator_angle
AttributeCreator_angle
    ATTR_TABLE:
      SET_TO PCN.DotProduct = @Evaluate((@Value(CP.dx)*@Value(CN.dx))+(@Value(CP.dy)*@Value(CN.dy)))
      SET_TO PCN.LenProduct = @Evaluate(@Value(CP.Length)*@Value(CN.Length))
      SET_TO PCN.CosAngle = @Evaluate(@round(@Value(PCN.DotProduct)/@Value(PCN.LenProduct),14))
      SET_TO PCN.rad = @Evaluate(@acos(@Value(PCN.CosAngle)))
      SET_TO PCN.deg = @Evaluate(@Value(PCN.rad)*(180.0/@pi()) )
    -> AttributeCreator_direction
AttributeCreator_direction
    ATTR_TABLE:
      SET_TO CPr.dx = @Evaluate(@Value(CP.dy))
      SET_TO CPr.dy = @Evaluate(@Value(CP.dx)*(-1))
      SET_TO PCNr.DotProduct = @Evaluate((@Value(CPr.dx)*@Value(CN.dx))+(@Value(CPr.dy)*@Value(CN.dy)))
      SET_TO SignedDirection = @Evaluate(@abs(@Value(PCNr.DotProduct))==0 ? 1 : @Value(PCNr.DotProduct)/@abs(@Value(PCNr.DotProduct)))
      SET_TO AngularChange.Current = @Evaluate(@round(@Value(PCN.deg)*@Value(SignedDirection),10))
    -> MeasureSetter_Current

Bookmark: UpdateAngularChangeMeasures
MeasureSetter_Current
    GEOM_TYPE = Individual Vertex by Index
    INDEX = @Value(LoopIndex.C)
    MEASURE_NAME = $(MEASURE_NAME)
    MEASURE_VAL = @Value(AngularChange.Current)
    -> Tester_ClosedRing.C
Tester_ClosedRing.C
    BOOL_OP = AND
    TEST_CLAUSE:
      TEST @Value(_vertex.C.x) = @Value(_vertex.0.x)
      TEST @Value(_vertex.C.y) = @Value(_vertex.0.y)
    TEST_MODE = TEST
    PASSED -> MeasureSetter_Origin
    FAILED -> AttributeCreator_LoopEnds_2
MeasureSetter_Origin
    GEOM_TYPE = Individual Vertex by Index
    INDEX = @Value(LoopIndex.Min)
    MEASURE_NAME = $(MEASURE_NAME)
    MEASURE_VAL = @Value(AngularChange.Current)
    -> AttributeCreator_LoopEnds_3

Bookmark: NextLoop Indexer
AttributeCreator_LoopEnds_3
    ATTR_TABLE:
      SET_TO LoopIndex.Min = @Evaluate(@Value(LoopIndex.C)+1)
      SET_TO LoopIndex.P = @Value(LoopIndex.Min)
      SET_TO LoopIndex.C = @Evaluate(@Value(LoopIndex.P)+1)
      SET_TO LoopIndex.N = @Evaluate(@Value(LoopIndex.C)+1)
    -> Loop (output)
AttributeCreator_LoopEnds_2
    ATTR_TABLE:
      SET_TO LoopClosed.N = @Evaluate(@Value(_vertex.N.x)==@Value(_vertex.0.x) && @Value(_vertex.N.y)==@Value(_vertex.0.y))
      SET_TO LoopIndex.N = @Evaluate(@Value(LoopClosed.N) ? @Value(LoopIndex.Min)+1 : @Value(LoopIndex.N)+1)
      SET_TO LoopIndex.C = @Evaluate(@Value(LoopIndex.C)+1)
      SET_TO LoopIndex.P = @Evaluate(@Value(LoopIndex.P)+1)
    -> Loop (output)

FME custom transformer AngularChangeLocator

Parameters:
- MaxOrthogonalAngleError = 10   # Maximum error on orthogonal angles (deg)
- MaxCollinearAngleError = 2.5   # Maximum error on collinear angles (deg)

Input (input)
    -> MeasureSetter
Note: Angular classification measure (AngularType) / 0 Orthogonal [(90-Maximum error on orthogonal angles), 90] / 1 Collinear1 [0, Maximum error on collinear angles] / 2 Collinear2 [Maximum error on collinear angles, Maximum error on orthogonal angles] / 3 Non-orthogonal [Maximum error on orthogonal angles, (90-Maximum error on orthogonal angles)] / Collinear angles provide no meaningful information. The last significant type [0,3] moving forward and backward is kept instead and the angular changes are added together and used to classify collinear angles.
Loop (input)
    -> AttributeCreator_3
AttributeCreator_3
    ATTR_TABLE:
      SET_TO _index.forward.current = @Evaluate(@Value(_index.forward.current)+1)
      SET_TO _index.backward.current = @Evaluate(@Value(_index.backward.current)-1)
    -> Tester_2
Tester_2
    BOOL_OP = AND
    TEST_CLAUSE:
      TEST @Value(_index.forward.current) > @Value(_index.max)
      TEST @Value(_index.backward.current) < 0
    TEST_MODE = TEST
    PASSED -> AttributeRemover_3
    FAILED -> MeasureExtractor.angularChange.F
AttributeRemover
    REMOVE_ATTRS = _index.forward.defined,_vertex.C0,_index.forward,_index.max,_index.backward.current,_vertex.C1,_index.backward,_angularType.measure,_index.forward.current,_vertex.C2,_index.backward.defined,_index.change,_angularType.backward,_angularType.change,_angularChange,_vertex.C3,_angularType.vertex,_angularType.forward
    -> Changes (output)
Changes (output)
Loop (output)
AttributeRemover_3
    REMOVE_ATTRS = _index.backward.current,_vertex.C0,_vertex.C1,_index.forward.defined,_angularChange,_angularType.change,_angularType.measure,_index.forward,_vertex.C3,_index.backward.defined,_angularType.vertex,_angularType.forward,_index.backward,_index.forward.current,_index.max,_vertex.C2
    -> AttributeRenamer_3
AttributeRenamer_3
    ATTR_TABLE = RENAME_SET_DEFAULT _angularType.backward > _angularType.origin
    -> Output (output)
Output (output)

Bookmark: InitializeVariables
MeasureSetter
    GEOM_TYPE = All Vertices to Same Value
    MEASURE_NAME = AngularType
    MEASURE_VAL = 9
    -> MeasureExtractor_C_2
MeasureExtractor_C_2
    GEOM_TYPE = Individual Vertex by Index
    INDEX = 0
    MEASURE_ATTR = _angularChange
    MEASURE_NAME = AngularChange
    -> AttributeCreator_0
AttributeCreator_0
    ATTR_TABLE:
      SET_TO _index.max = @Evaluate(@NumCoords()-1)
      SET_TO _index.forward.current = 0
      SET_TO _index.forward.defined = 0
      SET_TO _index.backward.current = @Value(_index.max)
      SET_TO _index.backward.defined = @Value(_index.max)
      SET_TO _angularType.forward = @Evaluate(@max(@abs(@Value(_angularChange)),90)-@min(@abs(@Value(_angularChange)),90)<= $(MaxOrthogonalAngleError) ? 0 : 3)
      SET_TO _angularType.backward = @Value(_angularType.forward)
    -> Tester_2

Bookmark: LoopForward
MeasureExtractor.angularChange.F
    GEOM_TYPE = Individual Vertex by Index
    INDEX = @Value(_index.forward.current)
    MEASURE_ATTR = _angularChange
    MEASURE_NAME = AngularChange
    -> AttributeCreator.F0
AttributeCreator.F0
    ATTR_TABLE:
      SET_TO _vertex.C0 = @Evaluate(@max(@abs(@Value(_angularChange)),90)-@min(@abs(@Value(_angularChange)),90)<= $(MaxOrthogonalAngleError) ? 0 : -1)
      SET_TO _vertex.C1 = @Evaluate(@abs(@Value(_angularChange))<=$(MaxCollinearAngleError) ? 1 : -1)
      SET_TO _vertex.C2 = @Evaluate(@abs(@Value(_angularChange))<=$(MaxOrthogonalAngleError) && @Value(_vertex.C1)<0 ? 2 : -1)
      SET_TO _vertex.C3 = @Evaluate(@abs(@Value(_angularChange))>$(MaxOrthogonalAngleError) && @Value(_vertex.C0)<0 ? 3 : -1)
      SET_TO _angularType.vertex = @Evaluate(@max(@Value(_vertex.C0),@Value(_vertex.C1),@Value(_vertex.C2),@Value(_vertex.C3)))
      SET_TO _angularType.change = @Evaluate(@Value(_angularType.vertex)-@Value(_angularType.forward))
    -> Tester_Defined.F
    -> Tester_Change.F
Tester_Change.F
    BOOL_OP = AND
    TEST_CLAUSE:
      TEST @Value(_angularType.change) IN 3,-3
      TEST @Value(_angularType.vertex) IN 0,3
    TEST_MODE = TEST
    PASSED -> AttributeCreator.F3
AttributeCreator.F3
    ATTR_TABLE = SET_TO _index.change = @Evaluate(@Value(_angularType.change)>0 ? @Value(_index.forward.current) : @Value(_index.forward.defined))
    -> Forward
Forward: Geometry2Point
    IND = @Value(_index.change)
    -> Forward_Output
    -> AttributeRemover
Forward_Output: Inspector [off]
Tester_Defined.F
    BOOL_OP = OR
    TEST_CLAUSE = TEST @Value(_angularType.vertex) IN 0,3
    TEST_MODE = TEST
    PASSED -> AttributeCreator.F2
    FAILED -> MeasureExtractor.angularType.F
AttributeCreator.F2
    ATTR_TABLE:
      SET_TO _angularType.measure = @Value(_angularType.vertex)
      SET_TO _angularType.forward = @Value(_angularType.vertex)
      SET_TO _index.forward.defined = @Value(_index.forward.current)
    -> MeasureSetter.F
MeasureExtractor.angularType.F
    GEOM_TYPE = Individual Vertex by Index
    INDEX = @Value(_index.forward.current)
    MEASURE_ATTR = _angularType.measure
    MEASURE_NAME = AngularType
    -> AttributeCreator.F1
AttributeCreator.F1
    ATTR_TABLE = SET_TO _angularType.measure = @Evaluate(@min(@Value(_angularType.forward),@Value(_angularType.measure)))
    -> MeasureSetter.F
MeasureSetter.F
    GEOM_TYPE = Individual Vertex by Index
    INDEX = @Value(_index.forward.current)
    MEASURE_NAME = AngularType
    MEASURE_VAL = @Value(_angularType.measure)
    -> MeasureExtractor.angularChange.B

Bookmark: LoopBackward
MeasureExtractor.angularChange.B
    GEOM_TYPE = Individual Vertex by Index
    INDEX = @Value(_index.backward.current)
    MEASURE_ATTR = _angularChange
    MEASURE_NAME = AngularChange
    -> AttributeCreator.B0
AttributeCreator.B0
    ATTR_TABLE:
      SET_TO _vertex.C0 = @Evaluate(@max(@abs(@Value(_angularChange)),90)-@min(@abs(@Value(_angularChange)),90)<= $(MaxOrthogonalAngleError) ? 0 : -1)
      SET_TO _vertex.C1 = @Evaluate(@abs(@Value(_angularChange))<=$(MaxCollinearAngleError) ? 1 : -1)
      SET_TO _vertex.C2 = @Evaluate(@abs(@Value(_angularChange))<=$(MaxOrthogonalAngleError) && @Value(_vertex.C1)<0 ? 2 : -1)
      SET_TO _vertex.C3 = @Evaluate(@abs(@Value(_angularChange))>$(MaxOrthogonalAngleError) && @Value(_vertex.C0)<0 ? 3 : -1)
      SET_TO _angularType.vertex = @Evaluate(@max(@Value(_vertex.C0),@Value(_vertex.C1),@Value(_vertex.C2),@Value(_vertex.C3)))
      SET_TO _angularType.change = @Evaluate(@Value(_angularType.vertex)-@Value(_angularType.backward))
    -> Tester_Defined.B
    -> Tester_Change.B
Tester_Change.B
    BOOL_OP = AND
    TEST_CLAUSE:
      TEST @Value(_angularType.change) IN 3,-3
      TEST @Value(_angularType.vertex) IN 0,3
    TEST_MODE = TEST
    PASSED -> AttributeCreator.B3
AttributeCreator.B3
    ATTR_TABLE = SET_TO _index.change = @Evaluate(@Value(_angularType.change)>0 ? @Value(_index.backward.current) : @Value(_index.backward.defined))
    -> backward
backward: Geometry2Point
    IND = @Value(_index.change)
    -> backward_Output
    -> AttributeRemover
backward_Output: Inspector [off]
Tester_Defined.B
    BOOL_OP = OR
    TEST_CLAUSE = TEST @Value(_angularType.vertex) IN 0,3
    TEST_MODE = TEST
    PASSED -> AttributeCreator.B2
    FAILED -> MeasureExtractor.angularType.B
AttributeCreator.B2
    ATTR_TABLE:
      SET_TO _angularType.measure = @Value(_angularType.vertex)
      SET_TO _angularType.backward = @Value(_angularType.vertex)
      SET_TO _index.backward.defined = @Value(_index.backward.current)
    -> MeasureSetter.B
MeasureExtractor.angularType.B
    GEOM_TYPE = Individual Vertex by Index
    INDEX = @Value(_index.backward.current)
    MEASURE_ATTR = _angularType.measure
    MEASURE_NAME = AngularType
    -> AttributeCreator.B1
AttributeCreator.B1
    ATTR_TABLE = SET_TO _angularType.measure = @Evaluate(@min(@Value(_angularType.backward),@Value(_angularType.measure)))
    -> MeasureSetter.B
MeasureSetter.B
    GEOM_TYPE = Individual Vertex by Index
    INDEX = @Value(_index.backward.current)
    MEASURE_NAME = AngularType
    MEASURE_VAL = @Value(_angularType.measure)
    -> Loop (output)
